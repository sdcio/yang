module srl_nokia-bgp {
  yang-version 1.1;
  namespace "urn:nokia.com:srlinux:bgp:bgp";
  prefix srl_nokia-bgp;

  import srl_nokia-common {
    prefix srl_nokia-comm;
  }
  import srl_nokia-network-instance {
    prefix srl_nokia-netinst;
  }
  import srl_nokia-segment-routing {
    prefix srl_nokia-sr;
  }
  import srl_nokia-extensions {
    prefix srl_nokia-ext;
  }
  import srl_nokia-routing-policy {
    prefix srl-rpol;
  }
  import srl_nokia-system {
    prefix srl_nokia-system;
  }
  import srl_nokia-mpls-label-management {
    prefix srl_nokia-mplslbl;
  }
  import srl_nokia-system-protocols {
    prefix srl_nokia-system-protocols;
  }
  import srl_nokia-keychains {
    prefix srl-keychain;
  }
  import srl_nokia-features {
    prefix srl_nokia-feat;
  }

  organization
    "Nokia";
  contact
    "Nokia SR Linux Support
     Web: <http://www.nokia.com>";
  description
    "This yang file models configuration and state of the BGP protocol";

  revision 2024-07-31 {
    description
      "SRLinux 24.7.1";
  }
  revision 2024-03-31 {
    description
      "SRLinux 24.3.1";
  }
  revision 2023-10-31 {
    description
      "SRLinux 23.10.1";
  }
  revision 2023-07-31 {
    description
      "SRLinux 23.7.1";
  }
  revision 2023-03-31 {
    description
      "SRLinux 23.3.1";
  }
  revision 2022-11-30 {
    description
      "SRLinux 22.11.1";
  }
  revision 2022-06-30 {
    description
      "SRLinux 22.6.1";
  }
  revision 2022-03-31 {
    description
      "SRLinux 22.3.1";
  }
  revision 2021-11-30 {
    description
      "SRLinux 21.11.1";
  }
  revision 2021-06-30 {
    description
      "SRLinux 21.6.1";
  }
  revision 2021-03-31 {
    description
      "SRLinux 21.3.1";
  }
  revision 2020-06-30 {
    description
      "SRLinux 20.6.1";
  }
  revision 2019-11-30 {
    description
      "SRLinux 19.11.1";
  }

  typedef ip-ecmp {
    description
      "The supported range of ECMP values for IP routes.";
    type uint32 {
      range "1..64";
    }
  }

  typedef percentage {
    type uint8 {
      range "0..100";
    }
    description
      "Integer indicating a percentage value";
  }

  typedef cluster-id-type {
    type union {
      type uint32 {
        range "1..max" {
          error-message "cluster-id cannot be 0";
        }
      }
      type srl_nokia-comm:dotted-quad {
      }
    }
  }

  grouping bgp-policy {
    leaf-list export-policy {
      description
        "Apply an export policy to advertised BGP routes";
      ordered-by user;
      max-elements 14;
      type leafref {
        path "/srl-rpol:routing-policy/srl-rpol:policy/srl-rpol:name";
      }
    }
    leaf-list import-policy {
      description
        "Apply an import policy to received BGP routes";
      ordered-by user;
      max-elements 14;
      type leafref {
        path "/srl-rpol:routing-policy/srl-rpol:policy/srl-rpol:name";
      }
    }
  }

  grouping bgp-afi-safi-policy {
    leaf-list export-policy {
      if-feature "srl_nokia-feat:bgp-afi-safi-policy";
      description
        "Apply an export policy to advertised BGP routes";
      ordered-by user;
      max-elements 14;
      type leafref {
        path "/srl-rpol:routing-policy/srl-rpol:policy/srl-rpol:name";
      }
    }
    leaf-list import-policy {
      if-feature "srl_nokia-feat:bgp-afi-safi-policy";
      description
        "Apply an import policy to received BGP routes";
      ordered-by user;
      max-elements 14;
      type leafref {
        path "/srl-rpol:routing-policy/srl-rpol:policy/srl-rpol:name";
      }
    }
  }

  grouping traceoptions {
    container trace-options {
      description
        "Debug traceoptions for BGP";
      list flag {
        key "name";
        description
          "Tracing parameters";
        leaf name {
          type enumeration {
            enum events {
              value 0;
              description
                "Trace all BGP events.";
            }
            enum packets {
              value 1;
              description
                "Trace all BGP protocol packets.";
            }
            enum open {
              value 2;
              description
                "Trace BGP open packets.";
            }
            enum keepalive {
              value 3;
              description
                "Trace BGP keepalive packets.";
            }
            enum graceful-restart {
              value 4;
              description
                "Trace Graceful Restart events.";
            }
            enum timers {
              value 5;
              description
                "Trace routing protocol timer processing.";
            }
            enum route {
              description
                "Trace BGP route table manager.";
              value 6;
            }
            enum notification {
              description
                "Trace Bgp notification.";
              value 7;
            }
            enum socket {
              description
                "Trace socket info.";
              value 8;
            }
            enum update {
              description
                "Trace update info.";
              value 9;
            }
          }
        }
        leaf modifier {
          type enumeration {
            enum detail {
              value 0;
              description
                "To enable detailed tracing. Includes both received and sent packets.";
            }
            enum receive {
              value 1;
              description
                "To enable tracing for the packets which are received.";
            }
            enum send {
              value 2;
              description
                "To enable tracing for the sent packets.";
            }
          }
        }
      }
    }
  }

  grouping rfc-8950-instance {
    leaf advertise-ipv6-next-hops {
      type boolean;
      description
        "Enables advertisement of IPv4 routes with IPv6 next-hops";
      default "false";
    }
    leaf receive-ipv6-next-hops {
      type boolean;
      description
        "Enables the advertisement of the RFC 8950 capability to receive IPv4 routes with IPv6 next-hops

         When set to true, BGP advertises an extended NH encoding (RFC 8950) capability to its peers. This capability indicates that local router is prepared to accept BGP routes for the AFI/SAFI with IPv6 next-hops from  peers in the scope of the command. When set to false, BGP handles received AFI/SAFI routes with IPv6 next-hops as an error and applies treat-as-withdraw.";
      default "false";
    }
  }

  grouping rfc-8950-group-neighbor {
    leaf advertise-ipv6-next-hops {
      type boolean;
      description
        "Enables advertisement of IPv4 routes with IPv6 next-hops";
    }
    leaf receive-ipv6-next-hops {
      type boolean;
      description
        "Enables the advertisement of the RFC 8950 capability to receive IPv4 routes with IPv6 next-hops

         When set to true, BGP advertises an extended NH encoding (RFC 8950) capability to its peers. This capability indicates that local router is prepared to accept BGP routes for the AFI/SAFI with IPv6 next-hops from  peers in the scope of the command. When set to false, BGP handles received AFI/SAFI routes with IPv6 next-hops as an error and applies treat-as-withdraw.";
    }
  }

  grouping optional-attributes-group {
    container optional-attributes {
      if-feature "srl_nokia-feat:bgp-labeled-unicast-prefix-sid or srl_nokia-feat:bgp-accumulated-igp-metric";
      leaf block-prefix-sid {
        if-feature "srl_nokia-feat:bgp-labeled-unicast-prefix-sid";
        description
          "Remove the prefix SID optional transitive attribute in all received and sent routes to this peer, or group of peers";
        type boolean;
        default "false";
        must ". = false() or current()/../../../../../srl_nokia-netinst:type = 'srl_nokia-netinst:default'" {
          error-message "block-prefix-sid cannot be enabled in network instance other than default";
        }
      }
    }
  }

  grouping optional-attributes-neighbor {
    container optional-attributes {
      if-feature "srl_nokia-feat:bgp-labeled-unicast-prefix-sid or srl_nokia-feat:bgp-accumulated-igp-metric";
      leaf block-prefix-sid {
        if-feature "srl_nokia-feat:bgp-labeled-unicast-prefix-sid";
        description
          "Remove the prefix SID optional transitive attribute in all received and sent routes to this peer, or group of peers";
        type boolean;
        must "current()/../../../../../srl_nokia-netinst:type = 'srl_nokia-netinst:default'" {
          error-message "block-prefix-sid cannot be configured in network instance other than default";
        }
      }
    }
  }

  grouping bgp-group {
    list group {
      key "group-name";
      description
        "Peer group templates";
      leaf group-name {
        type srl_nokia-comm:name {
          length "1..64";
        }
        description
          "The configured name of the peer group";
      }
      leaf admin-state {
        type srl_nokia-comm:admin-state;
        default "enable";
        must ". = 'disable' or
              (((not(../afi-safi[afi-safi-name='ipv4-unicast']/admin-state) and ../../afi-safi[afi-safi-name='ipv4-unicast']/admin-state = 'enable') or (../afi-safi[afi-safi-name='ipv4-unicast']/admin-state = 'enable')) or
              ((not(../afi-safi[afi-safi-name='ipv6-unicast']/admin-state) and ../../afi-safi[afi-safi-name='ipv6-unicast']/admin-state = 'enable') or (../afi-safi[afi-safi-name='ipv6-unicast']/admin-state = 'enable')) or
              ((not(../afi-safi[afi-safi-name='evpn']/admin-state) and ../../afi-safi[afi-safi-name='evpn']/admin-state = 'enable') or (../afi-safi[afi-safi-name='evpn']/admin-state = 'enable')) or
              ((not(../afi-safi[afi-safi-name='l3vpn-ipv4-unicast']/admin-state) and ../../afi-safi[afi-safi-name='l3vpn-ipv4-unicast']/admin-state = 'enable') or (../afi-safi[afi-safi-name='l3vpn-ipv4-unicast']/admin-state = 'enable')) or
              ((not(../afi-safi[afi-safi-name='l3vpn-ipv6-unicast']/admin-state) and ../../afi-safi[afi-safi-name='l3vpn-ipv6-unicast']/admin-state = 'enable') or (../afi-safi[afi-safi-name='l3vpn-ipv6-unicast']/admin-state = 'enable')) or
              ((not(../afi-safi[afi-safi-name='ipv4-labeled-unicast']/admin-state) and ../../afi-safi[afi-safi-name='ipv4-labeled-unicast']/admin-state = 'enable') or (../afi-safi[afi-safi-name='ipv4-labeled-unicast']/admin-state = 'enable')) or
              ((not(../afi-safi[afi-safi-name='ipv6-labeled-unicast']/admin-state) and ../../afi-safi[afi-safi-name='ipv6-labeled-unicast']/admin-state = 'enable') or (../afi-safi[afi-safi-name='ipv6-labeled-unicast']/admin-state = 'enable')) or
              ((not(../afi-safi[afi-safi-name='route-target']/admin-state) and ../../afi-safi[afi-safi-name='route-target']/admin-state = 'enable') or (../afi-safi[afi-safi-name='route-target']/admin-state = 'enable')) or
              ((not(../afi-safi[afi-safi-name='sr-policy-ipv4']/admin-state) and ../../afi-safi[afi-safi-name='sr-policy-ipv4']/admin-state = 'enable') or (../afi-safi[afi-safi-name='sr-policy-ipv4']/admin-state = 'enable')) or
              ((not(../afi-safi[afi-safi-name='sr-policy-ipv6']/admin-state) and ../../afi-safi[afi-safi-name='sr-policy-ipv6']/admin-state = 'enable') or (../afi-safi[afi-safi-name='sr-policy-ipv6']/admin-state = 'enable')))" {
          error-message "One of the address families must be enabled.";
        }
        description
          "Administratively enable or disable the peer group

           Disable will tear down all the BGP sessions in the group, even if they are administratively enabled at the neighbor level.";
      }
      leaf description {
        type srl_nokia-comm:description;
        description
          "A user provided description string for the peer group";
      }
      leaf under-maintenance {
        config false;
        type boolean;
        description
          "Indicates if this BGP group is in maintenance mode";
      }
      leaf maintenance-group {
        config false;
        type string;
        description
          "State field to display the maintenance group to which this group belongs to.";
      }
      uses bgp-policy;
      leaf local-preference {
        type uint32;
        description
          "The value of the local-preference attribute that is added to received routes from EBGP peers in the group

           It is also used to encode the local preference attribute for locally generated BGP routes.";
      }
      leaf next-hop-self {
        type boolean;
        default "false";
        description
          "When set to true, the next-hop in all IPv4-unicast, IPv6-unicast, EVPN, VPN-IPv4 and VPN-IPv6 BGP routes advertised to all IBGP peers in the peer-group is set equal to the local-address used on each session (or to the router ID if the NLRI is IPv6 and there is no IPv6 local address to use). This is independent of the route origin (EBGP, IBGP-client, IBGP-non-client or redistributed direct/static/aggregate route).

           When set to false, normal BGP rules from RFC 4271 apply.";
      }
      leaf peer-as {
        srl_nokia-ext:show-importance "high";
        type srl_nokia-comm:as-number;
        description
          "The autonomous system number expected from each peer in the group

           A configured session with a peer does not come up if this value does not match the AS value reported by the peer in its OPEN message.";
      }
      container as-path-options {
        description
          "Options for handling the AS_PATH in received BGP routes";
        leaf allow-own-as {
          type uint8;
          description
            "The maximum number of times the global AS number or a local AS number of the BGP instance can appear in any received AS_PATH before it is considered a loop and considered invalid

             When this value is changed the new value applies only to the routes received after the change is committed.";
        }
        container remove-private-as {
          presence "Configure remove-private-as";
          description
            "Container with options for removing private AS numbers (2-byte and 4-byte) from the advertised AS path towards all peers";
          leaf mode {
            description
              "The method by which private AS numbers are removed from the advertised AS_PATH attribute";
            type enumeration {
              enum disabled {
                description
                  "Do not strip or replace any private AS numbers";
              }
              enum delete {
                description
                  "Delete private AS numbers, shortening the AS path";
              }
              enum replace {
                description
                  "Replace private AS numbers with the local AS number used towards the peer, maintaining the AS path length";
              }
            }
            mandatory true;
          }
          leaf leading-only {
            description
              "If set to true then only delete or replace private AS numbers that appear before the first occurrence of a non-private ASN in the sequence of most recent ASNs in the AS path";
            type boolean;
            default "false";
            must "not(../mode = 'disabled' and . = true())" {
              error-message "mode should not be disabled to set leading-only to true.";
            }
          }
          leaf ignore-peer-as {
            description
              "If set to true then do not delete or replace a private AS number that is the same as the peer AS number";
            type boolean;
            default "false";
            must "not(../mode = 'disabled' and . = true())" {
              error-message "mode should not be disabled to set ignore-peer-as to true.";
            }
          }
        }
        leaf replace-peer-as {
          description
            "If set to true then replace every occurrence of the peer AS number that is present in the advertised AS path with the local AS number used towards the peer";
          type boolean;
        }
      }
      container authentication {
        description
          "Container with authentication options that apply to all peers in this peer-group";
        leaf keychain {
          description
            "Reference to a keychain. The keychain type must be tcp-md5.";
          type leafref {
            path "/srl_nokia-system:system/srl-keychain:authentication/srl-keychain:keychain/srl-keychain:name";
          }
          must '/srl_nokia-system:system/srl-keychain:authentication/srl-keychain:keychain[srl-keychain:name = current()]'
             + '/srl-keychain:type = "tcp-md5"' {
            error-message "Only keychain of type tcp-md5 can be assigned";
          }
        }
        leaf password {
          if-feature "srl_nokia-feat:bgp-auth-password";
          description
            "Configures an MD5 authentication password for use with neighboring devices.";
          type srl_nokia-comm:routing-password;
          must 'boolean(../keychain) = false()' {
            error-message "Can not assign both keychain and password";
          }
        }
      }
      container failure-detection {
        description
          "Options related to methods of detecting BGP session failure";
        leaf enable-bfd {
          if-feature "srl_nokia-feat:bfd";
          type boolean;
          description
            "The true setting enables Bi-directional Forwarding Detection on BGP sessions belonging to the peer group";
        }
        leaf fast-failover {
          type boolean;
          description
            "The true setting causes EBGP and IBGP sessions in the peer group to drop immediately (and not wait for hold timer expiry) when the local interface that they depend upon for neighbor reachability goes down";
        }
      }
      container multihop {
        description
          "Configuration parameters specifying the multihop behaviour for IBGP and EBGP peers in the peer group.";
        leaf admin-state {
          type srl_nokia-comm:admin-state;
          description
            "When enabled, IBGP and EBGP peers in the group are allowed to be indirectly connected by up to N hops, where N is controlled by the maximum-hops parameter. When disabled, only IBGP peers within the peer group support multihop.

             This can be overriden on a per neighbor basis. It is inherited by neighbors in the peer-group only if maximum-hops is also specified.

             By default this is disabled.";
        }
        leaf maximum-hops {
          type uint8 {
            range "1..255";
          }
          description
            "This sets the maximum number of routing hops towards each peer. It determines the IP TTL value in originated BGP TCP/IP packets. By default the TTL is set to 1 towards EBGP peers and 64 towards IBGP peers. This leaf sets a new IP TTL to use towards both EBGP and IBGP peers in the peer group.

             This can be overriden on a per neighbor basis. It is inherited by neighbors in the peer-group only if admin-state is also specified.";
        }
      }
      uses optional-attributes-group;
      container graceful-restart {
        description
          "Options related to router behavior as a graceful restart helper";
        leaf admin-state {
          type srl_nokia-comm:admin-state;
          description
            "Administratively enable or disable graceful restart helper for all address families";
        }
        leaf stale-routes-time {
          type uint16 {
            range "1..3600";
          }
          units "seconds";
          description
            "The maximum number of seconds that routes received from a neighbor that is being helped remain stale until they are deleted.

             Routes of AFI/SAFI X received from peer Y are marked stale when peer Y goes down and its previous GR capability included AFI/SAFI X.";
        }
        leaf requested-restart-time {
          if-feature "srl_nokia-feat:bgp-graceful-restart-gaps";
          description
            "The restart time encoded in this router's GR capability.

             If the neighbor honors this request then this is the maximum time allowed for this router to re-establish its TCP connection after a restart. If this time is exceeded, the neighbor is expected to flush stale routes that it was maintaining on behalf of this router.";
          type uint16 {
            range "1..3600";
          }
          units "seconds";
          default "300";
        }
      }
      list afi-safi {
        key "afi-safi-name";
        description
          "List of address families supported by the BGP peer group";
        leaf afi-safi-name {
          type identityref {
            base srl_nokia-comm:bgp-address-family;
          }
          description
            "The name of a BGP address family, which translates to a specific AFI value and a specific SAFI value";
          must "not(. = 'evpn') or /srl_nokia-netinst:network-instance[srl_nokia-netinst:name = current()/../../../../../srl_nokia-netinst:name]/srl_nokia-netinst:type = 'srl_nokia-netinst:default'" {
            error-message "EVPN is not supported in network instances other than default";
          }
          must "not(. = 'l3vpn-ipv4-unicast') or /srl_nokia-netinst:network-instance[srl_nokia-netinst:name = current()/../../../../../srl_nokia-netinst:name]/srl_nokia-netinst:type = 'srl_nokia-netinst:default'" {
            error-message "L3VPN is not supported in network instances other than default";
          }
          must "not(. = 'l3vpn-ipv6-unicast') or /srl_nokia-netinst:network-instance[srl_nokia-netinst:name = current()/../../../../../srl_nokia-netinst:name]/srl_nokia-netinst:type = 'srl_nokia-netinst:default'" {
            error-message "L3VPN is not supported in network instances other than default";
          }
          must "not(. = 'ipv4-labeled-unicast') or /srl_nokia-netinst:network-instance[srl_nokia-netinst:name = current()/../../../../../srl_nokia-netinst:name]/srl_nokia-netinst:type = 'srl_nokia-netinst:default'" {
            error-message "Label-ipv4 is not supported in network instances other than default";
          }
          must "not(. = 'ipv6-labeled-unicast') or /srl_nokia-netinst:network-instance[srl_nokia-netinst:name = current()/../../../../../srl_nokia-netinst:name]/srl_nokia-netinst:type = 'srl_nokia-netinst:default'" {
            error-message "Label-ipv6 is not supported in network instances other than default";
          }
          must "not(. = 'route-target') or /srl_nokia-netinst:network-instance[srl_nokia-netinst:name = current()/../../../../../srl_nokia-netinst:name]/srl_nokia-netinst:type = 'srl_nokia-netinst:default'" {
            error-message "route-target is not supported in network instances other than default";
          }
          must "not(. = 'sr-policy-ipv4') or /srl_nokia-netinst:network-instance[srl_nokia-netinst:name = current()/../../../../../srl_nokia-netinst:name]/srl_nokia-netinst:type = 'srl_nokia-netinst:default'" {
            error-message "sr-policy-ipv4 is not supported in network instances other than default";
          }
          must "not(. = 'sr-policy-ipv6') or /srl_nokia-netinst:network-instance[srl_nokia-netinst:name = current()/../../../../../srl_nokia-netinst:name]/srl_nokia-netinst:type = 'srl_nokia-netinst:default'" {
            error-message "sr-policy-ipv6 is not supported in network instances other than default";
          }
        }
        leaf admin-state {
          type srl_nokia-comm:admin-state;
          description
            "This leaf indicates whether the AFI-SAFI is enabled for the peer group";
        }
        uses bgp-afi-safi-policy;
        container add-paths {
          if-feature "srl_nokia-feat:bgp-add-paths";
          description
            "Configure support for the advertisement and receipt of multiple paths for the AFI/SAFI";
          leaf receive {
            type boolean;
            description
              "Enable capability negotiation to receive multiple path advertisements from a single peer for a single NLRI belonging to the AFI/SAFI";
            must "../../afi-safi-name != 'ipv4-labeled-unicast'" {
              srl_nokia-ext:if-feature "not srl_nokia-feat:bgp-add-paths-labeled-unicast";
              error-message "add-paths is not supported for address familiy ipv4-labeled-unicast";
            }
            must "../../afi-safi-name != 'ipv6-labeled-unicast'" {
              srl_nokia-ext:if-feature "not srl_nokia-feat:bgp-add-paths-labeled-unicast";
              error-message "add-paths is not supported for address familiy ipv6-labeled-unicast";
            }
            must "../../afi-safi-name != 'l3vpn-ipv4-unicast'" {
              srl_nokia-ext:if-feature "not srl_nokia-feat:bgp-add-paths-l3vpn";
              error-message "add-paths is not supported for address familiy l3vpn-ipv4-unicast";
            }
            must "../../afi-safi-name != 'l3vpn-ipv6-unicast'" {
              srl_nokia-ext:if-feature "not srl_nokia-feat:bgp-add-paths-l3vpn";
              error-message "add-paths is not supported for address familiy l3vpn-ipv6-unicast";
            }
            must "../../afi-safi-name != 'evpn'" {
              srl_nokia-ext:if-feature "not srl_nokia-feat:bgp-add-paths-evpn";
              error-message "add-paths is not supported for address familiy evpn";
            }
            must "../../afi-safi-name != 'route-target'" {
              error-message "add-paths is not supported for address family route-target";
            }
            must "../../afi-safi-name != 'sr-policy-ipv4'" {
              error-message "add-paths is not supported for address family sr-policy-ipv4";
            }
            must "../../afi-safi-name != 'sr-policy-ipv6'" {
              error-message "add-paths is not supported for address family sr-policy-ipv6";
            }
          }
          leaf send {
            type boolean;
            description
              "Enable capability negotiation to send multiple path advertisements to a single peer for a single NLRI belonging to the AFI/SAFI";
            must "../../afi-safi-name != 'ipv4-labeled-unicast'" {
              srl_nokia-ext:if-feature "not srl_nokia-feat:bgp-add-paths-labeled-unicast";
              error-message "add-paths is not supported for address familiy ipv4-labeled-unicast";
            }
            must "../../afi-safi-name != 'ipv6-labeled-unicast'" {
              srl_nokia-ext:if-feature "not srl_nokia-feat:bgp-add-paths-labeled-unicast";
              error-message "add-paths is not supported for address familiy ipv6-labeled-unicast";
            }
            must "../../afi-safi-name != 'l3vpn-ipv4-unicast'" {
              srl_nokia-ext:if-feature "not srl_nokia-feat:bgp-add-paths-l3vpn";
              error-message "add-paths is not supported for address familiy l3vpn-ipv4-unicast";
            }
            must "../../afi-safi-name != 'l3vpn-ipv6-unicast'" {
              srl_nokia-ext:if-feature "not srl_nokia-feat:bgp-add-paths-l3vpn";
              error-message "add-paths is not supported for address familiy l3vpn-ipv6-unicast";
            }
            must "../../afi-safi-name != 'evpn'" {
              srl_nokia-ext:if-feature "not srl_nokia-feat:bgp-add-paths-evpn";
              error-message "add-paths is not supported for address familiy evpn";
            }
            must "../../afi-safi-name != 'route-target'" {
              error-message "add-paths is not supported for address family route-target";
            }
            must "../../afi-safi-name != 'sr-policy-ipv4'" {
              error-message "add-paths is not supported for address family sr-policy-ipv4";
            }
            must "../../afi-safi-name != 'sr-policy-ipv6'" {
              error-message "add-paths is not supported for address family sr-policy-ipv6";
            }
          }
          choice selection-algorithm {
            leaf send-max {
              type uint8 {
                range "1..16";
              }
              description
                "Send the N best paths for a single NLRI, or as many as possible until there are no more valid paths to send.

                 This ensures the best path is advertised but does not limit the additional paths to being 'used' paths.";
              must '../send = true()' {
                error-message "send capability must be advertised";
              }
            }
            leaf send-multipath {
              type empty;
              description
                "Send the used paths for a single NLRI, including all paths that are multipaths.";
              must '../send = true()' {
                error-message "send capability must be advertised";
              }
            }
          }
        }
        container ipv4-unicast {
          description
            "Options related to the IPv4-unicast address family";
          uses rfc-8950-group-neighbor;
          container prefix-limit-received {
            description
              "Options for configuring the maximum number of IPv4 routes allowed to be received from each peer in the group";
            leaf max-received-routes {
              type uint32 {
                range "1..4294967295";
              }
              default "4294967295";
              description
                "Maximum number of IPv4 routes that will be accepted from each neighbor, counting routes accepted and rejected by import policies";
            }
            leaf warning-threshold-pct {
              type percentage;
              default "90";
              description
                "When the number of IPv4 routes received from any group peer (counting routes accepted and rejected by import policy) reaches this percentage of the max-received-routes limit, BGP raises a warning log event";
            }
            leaf prevent-teardown {
              if-feature "srl_nokia-feat:bgp-prefix-limit";
              type boolean;
              default "false";
              description
                "When false the session is immediately torn down when the number of received IPv4 routes exceeds the configured limit.";
            }
          }
          uses link-bandwidth;
        }
        container ipv4-labeled-unicast {
          if-feature "srl_nokia-feat:bgp-labeled-unicast";
          description
            "Options related to the labeled-IPv4-unicast address family";
          uses rfc-8950-group-neighbor {
            if-feature "srl_nokia-feat:bgp-labeled-unicast-future";
          }
          leaf next-hop-unchanged {
            if-feature "srl_nokia-feat:bgp-labeled-unicast-future";
            type boolean;
            default "false";
            description
              "When set to true, do not change the BGP next-hop towards group peers, even if next-hop-self is normally performed";
          }
          container prefix-limit-received {
            if-feature "srl_nokia-feat:bgp-labeled-unicast-future";
            description
              "Options for configuring the maximum number of label-IPv4 routes allowed to be received from each peer in the group";
            leaf max-received-routes {
              type uint32 {
                range "1..4294967295";
              }
              default "4294967295";
              description
                "Maximum number of label-IPv4 routes that will be accepted from each neighbor, counting routes accepted and rejected by import policies";
            }
            leaf warning-threshold-pct {
              type percentage;
              default "90";
              description
                "When the number of label-IPv4 routes received from any group peer (counting routes accepted and rejected by import policy) reaches this percentage of the max-received-routes limit, BGP raises a warning log event";
            }
            leaf prevent-teardown {
              if-feature "srl_nokia-feat:bgp-prefix-limit";
              type boolean;
              default "false";
              description
                "When false the session is immediately torn down when the number of received label-IPv4 routes exceeds the configured limit.";
            }
          }
        }
        container l3vpn-ipv4-unicast {
          if-feature "srl_nokia-feat:inter-as-nhsrr-ipvpn or srl_nokia-feat:ipvpn";
          description
            "Options related to the VPN-IPv4 unicast address family";
          uses rfc-8950-group-neighbor;
          container prefix-limit-received {
            description
              "Options for configuring the maximum number of VPN-IPv4 unicast routes allowed to be received from each peer in the group";
            leaf max-received-routes {
              type uint32 {
                range "1..4294967295";
              }
              default "4294967295";
              description
                "Maximum number of VPN-IPv4 routes that will be accepted from each neighbor, counting routes accepted and rejected by import policies";
            }
            leaf warning-threshold-pct {
              type percentage;
              default "90";
              description
                "When the number of VPN-IPv4 routes received from any group peer (counting routes accepted and rejected by import policy) reaches this percentage of the max-received-routes limit, BGP raises a warning log event";
            }
            leaf prevent-teardown {
              if-feature "srl_nokia-feat:bgp-prefix-limit";
              type boolean;
              default "false";
              description
                "When false the session is immediately torn down when the number of received VPN-IPv4 routes exceeds the configured limit.";
            }
          }
        }
        container ipv6-unicast {
          description
            "Options related to the IPv6-unicast address family";
          container prefix-limit-received {
            description
              "Options for configuring the maximum number of IPv6 routes allowed to be received from each peer in the group";
            leaf max-received-routes {
              type uint32 {
                range "1..4294967295";
              }
              default "4294967295";
              description
                "Maximum number of IPv6 routes that will be accepted from each neighbor, counting routes accepted and rejected by import policies";
            }
            leaf warning-threshold-pct {
              type percentage;
              default "90";
              description
                "When the number of IPv6 routes received from any group peer (counting routes accepted and rejected by import policy) reaches this percentage of the max-received-routes limit, BGP raises a warning log event";
            }
            leaf prevent-teardown {
              if-feature "srl_nokia-feat:bgp-prefix-limit";
              type boolean;
              default "false";
              description
                "When false the session is immediately torn down when the number of received IPv6 routes exceeds the configured limit.";
            }
          }
          uses link-bandwidth;
        }
        container ipv6-labeled-unicast {
          if-feature "srl_nokia-feat:bgp-labeled-unicast";
          description
            "Options related to the labeled IPv6-unicast address family";
          leaf next-hop-unchanged {
            if-feature "srl_nokia-feat:bgp-labeled-unicast-future";
            type boolean;
            default "false";
            description
              "When set to true, do not change the BGP next-hop towards group peers, even if next-hop-self is normally performed";
          }
          container prefix-limit-received {
            if-feature "srl_nokia-feat:bgp-labeled-unicast-future";
            description
              "Options for configuring the maximum number of labeled IPv6 routes allowed to be received from each peer in the group";
            leaf max-received-routes {
              type uint32 {
                range "1..4294967295";
              }
              default "4294967295";
              description
                "Maximum number of labeled IPv6 routes that will be accepted from each neighbor, counting routes accepted and rejected by import policies";
            }
            leaf warning-threshold-pct {
              type percentage;
              default "90";
              description
                "When the number of labeled IPv6 routes received from any group peer (counting routes accepted and rejected by import policy) reaches this percentage of the max-received-routes limit, BGP raises a warning log event";
            }
            leaf prevent-teardown {
              if-feature "srl_nokia-feat:bgp-prefix-limit";
              type boolean;
              default "false";
              description
                "When false the session is immediately torn down when the number of received labeled IPv6 routes exceeds the configured limit.";
            }
          }
        }
        container l3vpn-ipv6-unicast {
          if-feature "srl_nokia-feat:inter-as-nhsrr-ipvpn or srl_nokia-feat:ipvpn";
          description
            "Options related to the VPN-IPv6 unicast address family";
          container prefix-limit-received {
            description
              "Options for configuring the maximum number of VPN-IPv6 unicast routes allowed to be received from each peer in the group";
            leaf max-received-routes {
              type uint32 {
                range "1..4294967295";
              }
              default "4294967295";
              description
                "Maximum number of VPN-IPv6 routes that will be accepted from each neighbor, counting routes accepted and rejected by import policies";
            }
            leaf warning-threshold-pct {
              type percentage;
              default "90";
              description
                "When the number of VPN-IPv6 routes received from any group peer (counting routes accepted and rejected by import policy) reaches this percentage of the max-received-routes limit, BGP raises a warning log event";
            }
            leaf prevent-teardown {
              if-feature "srl_nokia-feat:bgp-prefix-limit";
              type boolean;
              default "false";
              description
                "When false the session is immediately torn down when the number of received VPN-IPv6 routes exceeds the configured limit.";
            }
          }
        }
        container evpn {
          description
            "Options related to the EVPN address family";
          leaf advertise-ipv6-next-hops {
            type boolean;
            must "/srl_nokia-netinst:network-instance[srl_nokia-netinst:name = current()/../../../../../../srl_nokia-netinst:name]/srl_nokia-netinst:type = 'srl_nokia-netinst:default'" {
              error-message "EVPN is not supported in network instances other than default";
            }
            description
              "Enables advertisement of EVPN routes with IPv6 next-hops to peers in the peer-group

               If this is set to true and the local-address used towards the peer is an IPv6 address and BGP is supposed to apply next-hop-self then the route is advertised with the IPv6 local-address as the BGP next-hop. If this is set to false, then the EVPN route is advertised with an IPv4 next-hop.";
          }
          container prefix-limit-received {
            description
              "Options for configuring the maximum number of EVPN routes allowed to be received from each peer in the peer-group";
            leaf max-received-routes {
              type uint32 {
                range "1..4294967295";
              }
              default "4294967295";
              must ". = 4294967295 or (/srl_nokia-netinst:network-instance[srl_nokia-netinst:name = current()/../../../../../../../srl_nokia-netinst:name]/srl_nokia-netinst:type = 'srl_nokia-netinst:default')" {
                error-message "EVPN is not supported in network instances other than default";
              }
              description
                "Maximum number of EVPN routes that will be accepted from each neighbor, counting routes accepted and rejected by import policies";
            }
            leaf warning-threshold-pct {
              type percentage;
              default "90";
              must ". = 90 or (/srl_nokia-netinst:network-instance[srl_nokia-netinst:name = current()/../../../../../../../srl_nokia-netinst:name]/srl_nokia-netinst:type = 'srl_nokia-netinst:default')" {
                error-message "EVPN is not supported in network instances other than default";
              }
              description
                "When the number of EVPN routes received from the peer (counting routes accepted and rejected by import policy) reaches this percentage of the max-received-routes limit, BGP raises a warning log event";
            }
          }
          leaf default-received-encapsulation {
            if-feature "srl_nokia-feat:nhsrr-evpn";
            type enumeration {
              enum vxlan {
                value 1;
              }
              enum mpls {
                value 2;
              }
            }
            description
              "Indicates the encapsulation considered when the routes are received without BGP encapsulation extended community

               Most EVPN routes are usually received with a BGP encapsulation extended community that indicates the encapsulation
               and therefore how to interpret the value in the received Label fields of the routes. If no encapsulation is
               received, BGP will validate the route as MPLS or VXLAN or SRv6 depending on how this command is configured.";
          }
        }
        container route-target {
          if-feature "srl_nokia-feat:bgp-rtc";
          description
            "Options related to the RT constraint address family";
          leaf send-default-route {
            type boolean;
            default "false";
            description
              "When true the router advertises a synthetically generated default RTC route to each peer in the group";
          }
          container prefix-limit-received {
            description
              "Options for configuring the maximum number of RTC routes allowed to be received from the peer";
            leaf max-received-routes {
              type uint32 {
                range "1..4294967295";
              }
              default "4294967295";
              must ". = 4294967295 or (/srl_nokia-netinst:network-instance[srl_nokia-netinst:name = current()/../../../../../../../srl_nokia-netinst:name]/srl_nokia-netinst:type = 'srl_nokia-netinst:default')" {
                error-message "RTC is not supported in network instances other than default";
              }
              description
                "Maximum number of RTC routes that will be accepted from the neighbor, counting routes accepted and rejected by import policies";
            }
            leaf warning-threshold-pct {
              type percentage;
              must ". = 90 or (/srl_nokia-netinst:network-instance[srl_nokia-netinst:name = current()/../../../../../../../srl_nokia-netinst:name]/srl_nokia-netinst:type = 'srl_nokia-netinst:default')" {
                error-message "RTC is not supported in network instances other than default";
              }
              default "90";
              description
                "When the number of RTC routes received from the peer (counting routes accepted and rejected by import policy) reaches this percentage of the max-received-routes limit, BGP raises a warning log event";
            }
            leaf prevent-teardown {
              if-feature "srl_nokia-feat:bgp-prefix-limit";
              type boolean;
              default "false";
              description
                "When false the session is immediately torn down when the number of received RTC routes exceeds the configured limit.";
              must ". = false() or (/srl_nokia-netinst:network-instance[srl_nokia-netinst:name = current()/../../../../../../../srl_nokia-netinst:name]/srl_nokia-netinst:type = 'srl_nokia-netinst:default')" {
                error-message "RTC is not supported in network instances other than default";
              }
            }
          }
        }
      }
      container local-as {
        description
          "Options related to the local autonomous-system number advertised by this router to its peers";
        leaf as-number {
          type srl_nokia-comm:as-number;
          description
            "The local autonomous system number used to override the global ASN on this group of BGP sessions

             Sets the ASN value that this router sends in its OPEN message towards its peer in the group.";
        }
        leaf prepend-global-as {
          type boolean;
          description
            "When set to true, the global ASN value is prepended to the AS path in outbound routes towards each BGP peer in the group

             If a session is EBGP (peer-as is not equal to the local-as) then the local-as is prepended as the final step, so that the local-as is the first element in the AS_PATH received by the peer.";
          must '../as-number' {
            error-message "must have as-number to set prepend-global-as";
          }
        }
        leaf prepend-local-as {
          type boolean;
          description
            "When set to true, the local AS value is prepended to the AS path of inbound routes from each EBGP peer belonging to the group";
          must '../as-number' {
            error-message "must have as-number to set prepend-local-as";
          }
        }
      }
      leaf route-flap-damping {
        if-feature "srl_nokia-feat:bgp-route-flap-damping";
        description
          "Enable/disable route flap damping procedures for routes received from EBGP peers in the peer group

           This has no effect on routes received from IBGP peers within the peer group.";
        type boolean;
        default "false";
      }
      container route-reflector {
        description
          "Container with route reflection configuration options.";
        leaf client {
          description
            "When this is set to true all configured and dynamic BGP sessions that belong to the peer-group are considered RR clients.";
          type boolean;
        }
        leaf cluster-id {
          description
            "The cluster-id to insert into the CLUSTER_LIST attribute when reflecting routes received by or sent to each client in the peer-group. The default is inherited from instance level configuration.";
          type cluster-id-type;
        }
      }
      container send-community {
        description
          "Options for controlling the sending of BGP communities to peers in the group";
        leaf standard {
          type boolean;
          description
            "The false setting causes BGP to strip all standard (4 byte) communities from all outbound routes advertised to each peer in the group";
        }
        leaf large {
          type boolean;
          description
            "The false setting causes BGP to strip all large (12 byte) BGP communities from all outbound routes advertised to each peer in the group";
        }
      }
      container send-default-route {
        description
          "Options for controlling the generation of default routes towards group peers";
        leaf ipv4-unicast {
          type boolean;
          default "false";
          description
            "Enables the sending of a synthetically generated default IPv4 route [0/0] to each peer in the group";
        }
        leaf ipv6-unicast {
          type boolean;
          default "false";
          description
            "Enables the sending of a synthetically generated default IPv6 route [::/0] to each peer in the group";
        }
        leaf export-policy {
          type leafref {
            path "/srl-rpol:routing-policy/srl-rpol:policy/srl-rpol:name";
          }
          description
            "The name of a policy that should be applied to the advertised default routes, in order to set their attributes to non-default values

             Only the default-action of this policy is parsed and applied.";
        }
      }
      container timers {
        leaf connect-retry {
          type uint16 {
            range "1..65535";
          }
          units "seconds";
          default "120";
          description
            "The time interval in seconds between successive attempts to establish a session with a peer";
        }
        leaf hold-time {
          type uint16 {
            range "0|3..65535";
          }
          units "seconds";
          default "90";
          description
            "The hold-time interval in seconds that the router proposes to the peer in its OPEN message

             The actual in-use hold-time is negotiated to the lowest value proposed by the two peers. A negotiated value of 0 suppresses the sending of keepalives by both peers.";
        }
        leaf keepalive-interval {
          type uint16 {
            range "0..21845";
          }
          units "seconds";
          description
            "The interval in seconds between successive keepalive messages sent to the peer

             The period between one keepalive message and the next is the minimum of this configured value and 1/3 of the negotiated hold-time duration. A value of 0 suppresses the sending of keepalives to the peer.";
        }
        leaf minimum-advertisement-interval {
          type uint16 {
            range "1..255";
          }
          units "seconds";
          default "5";
          description
            "The value assigned to the MinRouteAdvertisementIntervalTimer of RFC 4271, for both EBGP and IBGP sessions

             Each session runs its own independent timer and the timer affects both route advertisements and route withdrawals, regardless of address family. For route withdrawals only, this timer is bypassed if rapid-withdrawal is set to true.";
        }
        leaf prefix-limit-restart-timer {
          if-feature "srl_nokia-feat:bgp-prefix-limit";
          type uint16;
          units "seconds";
          default "0";
          description
            "Time interval in seconds after which the BGP session is re-established after being torn down due to exceeding any prefix limit (of any address family)

             This only applies if prevent-teardown is false.";
        }
      }
      uses traceoptions;
      container transport {
        leaf mtu-discovery {
          if-feature "srl_nokia-feat:bgp-mtu-discovery";
          type boolean;
          description
            "Turns path mtu discovery for BGP TCP sessions on (true) or off (false)";
        }
        leaf tcp-mss {
          type uint16 {
            range "536..9446";
          }
          units "bytes";
          description
            "The maximum segment size of BGP TCP packets

             The actual value used in the transmit direction towards a particular peer should be checked at the neighbor level.";
        }
        leaf passive-mode {
          type boolean;
          default "false";
          description
            "The true setting causes BGP to wait for the peer to initiate the TCP connection

             The false setting causes BGP to initiate a TCP connection whenever the BGP session is started or restarted.";
        }
        leaf local-address {
          type union {
            type srl_nokia-comm:ip-address;
            type srl_nokia-comm:subinterface-all;
          }
          description
            "The local TCP endpoint of used for all BGP sessions in the group

             This also the source address for next-hop-self, if it applies. The local-address can be specified as an IP address that is resolvable to a local interface.

             This address must be the primary address of an interface, otherwise the session will not come up.";
        }
      }
      container statistics {
        description
          "Container for BGP statistics.";
        config false;
        leaf total-paths {
          type srl_nokia-comm:zero-based-counter64;
          description
            "The total number of path attribute objects used by received BGP routes associated with the peer-group";
        }
        leaf total-prefixes {
          config false;
          type uint64;
          description
            "The total number of unique NLRI contained in all received BGP routes associated with the BGP instance or the peer-group.";
        }
        leaf path-memory {
          type srl_nokia-comm:zero-based-counter64;
          description
            "The total number of bytes required to store the path attribute objects used by received BGP routes associated with the peer-group";
        }
        leaf total-received-routes {
          type srl_nokia-comm:zero-based-counter64;
          description
            "The total number of received BGP routes associated with the peer-group, summed across all address families";
        }
        leaf total-active-routes {
          type srl_nokia-comm:zero-based-counter64;
          description
            "The total number of received BGP routes that are active (installed for forwarding) and associated with the peer-group, summed across all address families";
        }
        leaf total-peers {
          type uint16;
          description
            "The total number of configured BGP peers associated with the peer-group";
        }
        leaf up-peers {
          type uint16;
          description
            "The number of configured BGP peers associated with the peer-group that are currently in the established state";
        }
        leaf disabled-peers {
          type uint16;
          description
            "The number of configured BGP peers associated with the peer-group that are administratively disabled";
        }
        leaf dynamic-peers {
          type uint16;
          description
            "The number of dynamic BGP peers associated with the peer-group that are currently in the established state, counting sessions resulting from accepted incoming TCP connections and outgoing TCP connections triggered by LLDP auto-discovery";
        }
      }
    }
  }

  grouping neighbor-state {
    leaf peer-router-id {
      config false;
      srl_nokia-ext:show-importance "high";
      description
        "The BGP identifier advertised by the peer in its OPEN message";
      type srl_nokia-comm:dotted-quad;
    }
    leaf session-state {
      config false;
      srl_nokia-ext:show-importance "high";
      type enumeration {
        enum idle {
          value 0;
        }
        enum connect {
          value 1;
        }
        enum active {
          value 2;
        }
        enum opensent {
          value 3;
        }
        enum openconfirm {
          value 4;
        }
        enum established {
          value 5;
        }
      }
      description
        "Current state of the session";
    }
    leaf last-state {
      config false;
      type enumeration {
        enum idle {
          value 0;
        }
        enum connect {
          value 1;
        }
        enum active {
          value 2;
        }
        enum opensent {
          value 3;
        }
        enum openconfirm {
          value 4;
        }
        enum established {
          value 5;
        }
      }
      description
        "Previous state of the session";
    }
    leaf last-event {
      config false;
      type enumeration {
        enum none;
        enum start;
        enum stop;
        enum open;
        enum close;
        enum openFail;
        enum error;
        enum connectRetry;
        enum holdTime;
        enum keepAlive;
        enum recvOpen;
        enum recvKeepAlive;
        enum recvUpdate;
        enum recvNotify;
        enum startPassive;
        enum parseError;
        enum outOfMemory;
        enum rtmLimitExceed;
        enum outOfProtNHIndex;
        enum outOfNHIndex;
        enum labelAllocFailed;
        enum lspIdAllocFailed;
        enum collisionResolution;
        enum adminShutdown;
        enum adminReset;
        enum configChange;
        enum maxPrefixExceed;
        enum maxPfxExcdLog;
        enum trackingPolMismatch;
        enum receivedMalformedAttr;
        enum adminResetHard;
        enum peerDamping;
      }
    }
    leaf last-established {
      config false;
      type srl_nokia-comm:date-and-time-delta;
      description
        "The time when the session last transitioned into or out of the established state

         Uptime or downtime of the session can be calculated from this state.";
    }
    leaf established-transitions {
      config false;
      type srl_nokia-comm:zero-based-counter64;
      description
        "The total number of times the BGP FSM transitioned into the established state for this peer";
    }
    leaf-list advertised-capabilities {
      config false;
      type enumeration {
        enum MP_BGP;
        enum ROUTE_REFRESH;
        enum EXT_NH_ENCODING;
        enum GRACEFUL_RESTART;
        enum 4-OCTET_ASN;
        enum ORF_SEND_EXCOMM;
        enum ORF_RECEIVE_EXCOMM;
      }
      description
        "List of BGP capabilities advertised by the local routing device to the peer";
    }
    leaf-list received-capabilities {
      config false;
      type enumeration {
        enum MP_BGP;
        enum ROUTE_REFRESH;
        enum EXT_NH_ENCODING;
        enum GRACEFUL_RESTART;
        enum 4-OCTET_ASN;
        enum ORF_SEND_EXCOMM;
        enum ORF_RECEIVE_EXCOMM;
        enum ADD_PATH;
        enum LONG_LIVED_GR;
      }
      description
        "List of BGP capabilities received by the local routing device from the peer";
    }
    leaf-list received-afi-safi {
      config false;
      type identityref {
        base srl_nokia-comm:bgp-address-family;
      }
      description
        "List of multiprotocol BGP address families supported by the peer, derived from the AFI/SAFI list in the MP-BGP capability received by the local routing device from the peer";
    }
    leaf-list received-end-of-rib {
      config false;
      type identityref {
        base srl_nokia-comm:bgp-address-family;
      }
      description
        "List of address families for which the peer has signaled the End of RIB marker";
    }
    leaf-list sent-end-of-rib {
      config false;
      type identityref {
        base srl_nokia-comm:bgp-address-family;
      }
      description
        "List of address families for which this router sent the peer an End of RIB marker";
    }
    leaf slow-peer {
      config false;
      type enumeration {
        enum yes;
        enum no;
        enum unknown;
      }
      description
        "Set to 'yes' if, after the last BGP restart, the session was in a lesser state than established when the min-wait-to-advertise timer expired

         Set to unknown if the min-wait-to-advertise time has not yet elapsed.";
    }
    leaf dynamic-neighbor {
      config false;
      type boolean;
      description
        "Indicates true if the neighbor is a dynamic peer that resulted from an accepted incoming TCP connection or an outgoing TCP connection triggered by LLDP auto-discovery";
    }
    leaf discovered-by-lldp {
      config false;
      type boolean;
      description
        "Set to true if the peer IP address is known through LLDP (irrespective of whether the final TCP connection was originated by this router or not)";
    }
    container sent-messages {
      config false;
      description
        "Container for state information about BGP messages sent to the peer.";
      leaf queue-depth {
        type uint32;
        description
          "The number of messages queued to be sent to the peer.";
      }
      leaf total-updates {
        type srl_nokia-comm:zero-based-counter64;
        description
          "Number of BGP UPDATE messages sent to the peer over the lifetime of its configuration or since the last clear.";
      }
      leaf total-non-updates {
        type uint64;
        description
          "Number of BGP NON UPDATE messages sent to the peer over the lifetime of its configuration or since the last clear.";
      }
      leaf route-refresh {
        type srl_nokia-comm:zero-based-counter64;
        description
          "Number of BGP ROUTE_REFRESH messages sent to the peer over the lifetime of its configuration or since the last clear.";
      }
      leaf total-messages {
        type srl_nokia-comm:zero-based-counter64;
        description
          "Total number of BGP messages sent to the peer over the lifetime of its configuration or since the last clear.";
      }
      leaf last-notification-time {
        type srl_nokia-comm:date-and-time-delta;
        description
          "Timestamp representing the time of the last Notification message sent to the peer.";
      }
      leaf last-notification-error-code {
        config false;
        type enumeration {
          enum "Message Header Error" {
            value 0;
          }
          enum "Open Message Error" {
            value 1;
          }
          enum "Update Message Error" {
            value 2;
          }
          enum "Hold Timer Error" {
            value 3;
          }
          enum "Finite State Machine Error" {
            value 4;
          }
          enum Cease {
            value 5;
          }
        }
        description
          "The error code in the last NOTIFICATION sent to this peer.";
      }
      leaf last-notification-error-subcode {
        config false;
        type enumeration {
          enum "Connection Not Synchronized" {
            value 0;
          }
          enum "Bad Message Length" {
            value 1;
          }
          enum "Bad Message Type" {
            value 2;
          }
          enum "Unsupported Version Number" {
            value 3;
          }
          enum "Bad Peer As" {
            value 4;
          }
          enum "Bad BGP Identifier" {
            value 5;
          }
          enum "Unsupported Optional Parameter";
          enum "Unacceptable Hold Time";
          enum "UPDATE Message Error subcodes";
          enum "Malformed Attribute List";
          enum "Unrecognized Well-known Attribute";
          enum "Missing Well-known Attribute";
          enum "Attribute Flags Error";
          enum "Attribute Length Error";
          enum "Invalid ORIGIN Attribute";
          enum "Invalid NEXT_HOP Attribute";
          enum "Optional Attribute Error";
          enum "Invalid Network Field";
          enum "Malformed AS_PATH";
          enum "Maximum Number of Prefixes Reached";
          enum "Administrative Shutdown";
          enum "Peer De-configured";
          enum "Administrative Reset";
          enum "Connection Rejected";
          enum "Other Configuration Change";
          enum "Connection Collision Resolution";
          enum "Out of Resources";
          enum Unspecific;
          enum "Hard Reset";
          enum "Unsupported Capability";
        }
        description
          "The error subcode in the last NOTIFICATION sent to this peer.";
      }
      leaf total-notifications {
        type uint32;
        description
          "Number of BGP Notification messages sent to the peer over the lifetime of its configuration or since the last clear.";
      }
    }
    container received-messages {
      config false;
      description
        "Container for state information about BGP messages received from the peer.";
      leaf queue-depth {
        type uint32;
        description
          "The number of messages received from the peer currently queued.";
      }
      leaf total-updates {
        type srl_nokia-comm:zero-based-counter64;
        description
          "Number of BGP UPDATE messages received from the peer over the lifetime of its configuration or since the last clear.";
      }
      leaf total-non-updates {
        type uint64;
        description
          "Number of BGP NON UPDATE messages received from the peer over the lifetime of its configuration or since the last clear.";
      }
      leaf malformed-updates {
        type srl_nokia-comm:zero-based-counter64;
        description
          "Number of BGP UPDATE messages received from the peer that were malformed but recoverable through treat-as-withdraw or attribute-discard (i.e. without session reset)";
      }
      leaf route-refresh {
        type srl_nokia-comm:zero-based-counter64;
        description
          "Number of BGP ROUTE_REFRESH messages received from the peer over the lifetime of its configuration or since the last clear.";
      }
      leaf total-messages {
        type srl_nokia-comm:zero-based-counter64;
        description
          "Total number of BGP messages received from the peer over the lifetime of its configuration or since the last clear.";
      }
      leaf last-update-time {
        type srl_nokia-comm:date-and-time-delta;
        description
          "The timestamp when the last UPDATE was received from this peer.";
      }
      leaf last-notification-time {
        type srl_nokia-comm:date-and-time-delta;
        description
          "Timestamp representing the time of the last Notification message received from the peer.";
      }
      leaf last-notification-error-code {
        config false;
        type enumeration {
          enum "Message Header Error" {
            value 0;
          }
          enum "Open Message Error" {
            value 1;
          }
          enum "Update Message Error" {
            value 2;
          }
          enum "Hold Timer Error" {
            value 3;
          }
          enum "Finite State Machine Error" {
            value 4;
          }
          enum Cease {
            value 5;
          }
        }
        description
          "The error code in the last NOTIFICATION received from this peer.";
      }
      leaf last-notification-error-subcode {
        config false;
        type enumeration {
          enum "Connection Not Synchronized" {
            value 0;
          }
          enum "Bad Message Length" {
            value 1;
          }
          enum "Bad Message Type" {
            value 2;
          }
          enum "Unsupported Version Number" {
            value 3;
          }
          enum "Bad Peer As" {
            value 4;
          }
          enum "Bad BGP Identifier" {
            value 5;
          }
          enum "Unsupported Optional Parameter";
          enum "Unacceptable Hold Time";
          enum "UPDATE Message Error subcodes";
          enum "Malformed Attribute List";
          enum "Unrecognized Well-known Attribute";
          enum "Missing Well-known Attribute";
          enum "Attribute Flags Error";
          enum "Attribute Length Error";
          enum "Invalid ORIGIN Attribute";
          enum "Invalid NEXT_HOP Attribute";
          enum "Optional Attribute Error";
          enum "Invalid Network Field";
          enum "Malformed AS_PATH";
          enum "Maximum Number of Prefixes Reached";
          enum "Administrative Shutdown";
          enum "Peer De-configured";
          enum "Administrative Reset";
          enum "Connection Rejected";
          enum "Other Configuration Change";
          enum "Connection Collision Resolution";
          enum "Out of Resources";
          enum Unspecific;
          enum "Hard Reset";
          enum "Unsupported Capability";
        }
        description
          "The error subcode in the last NOTIFICATION received from the peer.";
      }
      leaf total-notifications {
        type uint32;
        description
          "Number of BGP Notification messages received from the peer over the lifetime of its configuration or since the last clear.";
      }
    }
  }

  grouping bgp-neighbor {
    list neighbor {
      description
        "Create a configured BGP session";
      key "peer-address";
      leaf peer-address {
        type srl_nokia-comm:ip-address-with-zone;
        description
          "The transport address of the BGP peer

           The peer-address must be a valid IPv4 unicast address, IPv6 global unicast address or IPv6 link-local address. An IPv6 link-local address requires the interface scope to be identified, using a format such as fe80::1234%ethernet-1/1.1";
      }
      leaf admin-state {
        type srl_nokia-comm:admin-state;
        default "enable";
        description
          "Administratively enable or disable the peer

           Disable will tear down the BGP session (return it to IDLE state).";
        must ". = 'disable' or
              ../afi-safi[afi-safi-name='ipv4-unicast']/admin-state = 'enable' or ../afi-safi[afi-safi-name='ipv6-unicast']/admin-state = 'enable' or ../afi-safi[afi-safi-name='evpn']/admin-state = 'enable' or
              ../afi-safi[afi-safi-name='l3vpn-ipv4-unicast']/admin-state = 'enable' or ../afi-safi[afi-safi-name='l3vpn-ipv6-unicast']/admin-state = 'enable' or
              ../afi-safi[afi-safi-name='ipv4-labeled-unicast']/admin-state = 'enable' or ../afi-safi[afi-safi-name='ipv6-labeled-unicast']/admin-state = 'enable' or
              ../afi-safi[afi-safi-name='evpn']/admin-state = 'enable' or ../afi-safi[afi-safi-name='route-target']/admin-state = 'enable' or
              (not(../afi-safi[afi-safi-name='ipv4-unicast']/admin-state) and (../../group[group-name = current()/../peer-group]/afi-safi[afi-safi-name='ipv4-unicast']/admin-state = 'enable' or (not(../../group[group-name = current()/../peer-group]/afi-safi[afi-safi-name='ipv4-unicast']/admin-state) and ../../afi-safi[afi-safi-name='ipv4-unicast']/admin-state = 'enable')))  or
              (not(../afi-safi[afi-safi-name='ipv6-unicast']/admin-state) and (../../group[group-name = current()/../peer-group]/afi-safi[afi-safi-name='ipv6-unicast']/admin-state = 'enable' or (not(../../group[group-name = current()/../peer-group]/afi-safi[afi-safi-name='ipv6-unicast']/admin-state) and ../../afi-safi[afi-safi-name='ipv6-unicast']/admin-state = 'enable'))) or
              (not(../afi-safi[afi-safi-name='evpn']/admin-state) and (../../group[group-name = current()/../peer-group]/afi-safi[afi-safi-name='evpn']/admin-state = 'enable' or (not(../../group[group-name = current()/../peer-group]/afi-safi[afi-safi-name='evpn']/admin-state) and ../../afi-safi[afi-safi-name='evpn']/admin-state = 'enable'))) or
              (not(../afi-safi[afi-safi-name='l3vpn-ipv4-unicast']/admin-state) and (../../group[group-name = current()/../peer-group]/afi-safi[afi-safi-name='l3vpn-ipv4-unicast']/admin-state = 'enable' or (not(../../group[group-name = current()/../peer-group]/afi-safi[afi-safi-name='l3vpn-ipv4-unicast']/admin-state) and ../../afi-safi[afi-safi-name='l3vpn-ipv4-unicast']/admin-state = 'enable'))) or
              (not(../afi-safi[afi-safi-name='l3vpn-ipv6-unicast']/admin-state) and (../../group[group-name = current()/../peer-group]/afi-safi[afi-safi-name='l3vpn-ipv6-unicast']/admin-state = 'enable' or (not(../../group[group-name = current()/../peer-group]/afi-safi[afi-safi-name='l3vpn-ipv6-unicast']/admin-state) and ../../afi-safi[afi-safi-name='l3vpn-ipv6-unicast']/admin-state = 'enable'))) or
              (not(../afi-safi[afi-safi-name='ipv4-labeled-unicast']/admin-state) and (../../group[group-name = current()/../peer-group]/afi-safi[afi-safi-name='ipv4-labeled-unicast']/admin-state = 'enable' or (not(../../group[group-name = current()/../peer-group]/afi-safi[afi-safi-name='ipv4-labeled-unicast']/admin-state) and ../../afi-safi[afi-safi-name='ipv4-labeled-unicast']/admin-state = 'enable'))) or
              (not(../afi-safi[afi-safi-name='ipv6-labeled-unicast']/admin-state) and (../../group[group-name = current()/../peer-group]/afi-safi[afi-safi-name='ipv6-labeled-unicast']/admin-state = 'enable' or (not(../../group[group-name = current()/../peer-group]/afi-safi[afi-safi-name='ipv6-labeled-unicast']/admin-state) and ../../afi-safi[afi-safi-name='ipv6-labeled-unicast']/admin-state = 'enable'))) or
              (not(../afi-safi[afi-safi-name='route-target']/admin-state) and (../../group[group-name = current()/../peer-group]/afi-safi[afi-safi-name='route-target']/admin-state = 'enable' or (not(../../group[group-name = current()/../peer-group]/afi-safi[afi-safi-name='route-target']/admin-state) and ../../afi-safi[afi-safi-name='route-target']/admin-state = 'enable'))) or
              (not(../afi-safi[afi-safi-name='sr-policy-ipv4']/admin-state) and (../../group[group-name = current()/../peer-group]/afi-safi[afi-safi-name='sr-policy-ipv4']/admin-state = 'enable' or (not(../../group[group-name = current()/../peer-group]/afi-safi[afi-safi-name='sr-policy-ipv4']/admin-state) and ../../afi-safi[afi-safi-name='sr-policy-ipv4']/admin-state = 'enable'))) or
              (not(../afi-safi[afi-safi-name='sr-policy-ipv6']/admin-state) and (../../group[group-name = current()/../peer-group]/afi-safi[afi-safi-name='sr-policy-ipv6']/admin-state = 'enable' or (not(../../group[group-name = current()/../peer-group]/afi-safi[afi-safi-name='sr-policy-ipv6']/admin-state) and ../../afi-safi[afi-safi-name='sr-policy-ipv6']/admin-state = 'enable')))" {
          error-message "One of the address families must be enabled.";
        }
      }
      leaf description {
        type srl_nokia-comm:description;
        description
          "A user provided description string for the peer";
      }
      leaf under-maintenance {
        config false;
        type boolean;
        description
          "State field to determine if this bgp neighbor is in maintenance mode.";
      }
      leaf maintenance-group {
        config false;
        type string;
        description
          "State field to display the maintenance group to which this neighbor belongs to.";
      }
      leaf peer-type {
        config false;
        type enumeration {
          enum ibgp {
            description
              "Indicates that the peer is IBGP (local-as == peer-as).";
          }
          enum ebgp {
            description
              "Indicates that the peer is EBGP (local-as != peer-as).";
          }
        }
        description
          "The session type. The type is EBGP when the local AS and peer AS are different, and the type is IBGP when the local AS and peer AS have the same value.";
      }
      uses bgp-policy;
      leaf local-preference {
        type uint32;
        description
          "The value of the local-preference attribute that is added to received routes from the peer, if it is EBGP

           It is also used to encode the local preference attribute for locally generated BGP routes.";
      }
      leaf next-hop-self {
        type boolean;
        description
          "When set to true, the next-hop in all IPv4-unicast, IPv6-unicast and EVPN BGP routes advertised to the peer, if IBGP, is set equal to the local-address used on this session (or to the router ID if the NLRI is IPv6 and there is no IPv6 local address to use). This is independent of the route origin (EBGP, IBGP-client, IBGP-non-client or redistributed direct/static/aggregate route).

           When set to false, normal BGP rules from RFC 4271 apply.";
      }
      leaf peer-as {
        srl_nokia-ext:show-importance "high";
        type srl_nokia-comm:as-number;
        description
          "The autonomous system number expected from the peer

           A configured session with a peer does not come up if this value does not match the AS value reported by the peer in its OPEN message.";
      }
      leaf peer-group {
        type leafref {
          path "../../group/group-name";
        }
        mandatory true;
        description
          "A reference to the peer-group template to use for this BGP session

           This is not immutable.";
      }
      leaf last-prefix-limit-exceeded {
        config false;
        if-feature "srl_nokia-feat:bgp-prefix-limit-last-exceeded";
        type srl_nokia-comm:date-and-time-delta;
        description
          "Time when the neighbor last violated a configured prefix-limit for any AFI/SAFI

           This value is set/updated when any AFI/SAFI prefix-limit-exceeded leaf transitions from false/unset to true.";
      }
      container as-path-options {
        description
          "Options for handling the AS_PATH in received BGP routes";
        leaf allow-own-as {
          type uint8;
          description
            "The maximum number of times the global AS number or a local AS number of the BGP instance can appear in any received AS_PATH before it is considered a loop and considered invalid";
        }
        container remove-private-as {
          presence "configure remove-private-as";
          description
            "Container with options for removing private AS numbers (2-byte and 4-byte) from the advertised AS path towards all peers";
          leaf mode {
            description
              "The method by which private AS numbers are removed from the advertised AS_PATH attribute";
            type enumeration {
              enum disabled {
                description
                  "Do not strip or replace any private AS numbers";
              }
              enum delete {
                description
                  "Delete private AS numbers, shortening the AS path";
              }
              enum replace {
                description
                  "Replace private AS numbers with the local AS number used towards the peer, maintaining the AS path length";
              }
            }
            mandatory true;
          }
          leaf leading-only {
            description
              "If set to true then only delete or replace private AS numbers that appear before the first occurrence of a non-private ASN in the sequence of most recent ASNs in the AS path";
            type boolean;
            default "false";
            must "not(../mode = 'disabled' and . = true())" {
              error-message "mode should not be disabled to set leading-only to true.";
            }
          }
          leaf ignore-peer-as {
            description
              "If set to true then do not delete or replace a private AS number that is the same as the peer AS number";
            type boolean;
            default "false";
            must "not(../mode = 'disabled' and . = true())" {
              error-message "mode should not be disabled to set ignore-peer-as to true.";
            }
          }
        }
        leaf replace-peer-as {
          description
            "If set to true then replace every occurrence of the peer AS number that is present in the advertised AS path with the local AS number used towards the peer";
          type boolean;
        }
      }
      container authentication {
        description
          "Container with authentication options that apply to this specific peer";
        leaf keychain {
          description
            "Reference to a keychain. The keychain type must be tcp-md5.";
          type leafref {
            path "/srl_nokia-system:system/srl-keychain:authentication/srl-keychain:keychain/srl-keychain:name";
          }
          must '/srl_nokia-system:system/srl-keychain:authentication/srl-keychain:keychain[srl-keychain:name = current()]'
             + '/srl-keychain:type = "tcp-md5"' {
            error-message "Only keychain of type tcp-md5 can be assigned";
          }
        }
        leaf password {
          if-feature "srl_nokia-feat:bgp-auth-password";
          description
            "Configures an MD5 authentication password for use with neighboring devices.";
          type srl_nokia-comm:routing-password;
          must 'boolean(../keychain) = false()' {
            error-message "Can not assign both keychain and password";
          }
        }
        leaf transmit-active {
          config false;
          description
            "Reads true when the TCP segments being sent to the peer have authentication data.";
          type boolean;
        }
      }
      container failure-detection {
        description
          "Options related to methods of detecting BGP session failure";
        leaf enable-bfd {
          if-feature "srl_nokia-feat:bfd";
          type boolean;
          description
            "The true setting enables Bi-directional Forwarding Detection on BGP sessions belonging to the peer group";
        }
        leaf fast-failover {
          type boolean;
          description
            "The true setting the EBGP or IBGP session to drop immediately (and not wait for hold timer expiry) when the local interface that it depends upon for neighbor reachability goes down";
        }
      }
      container graceful-restart {
        description
          "Options related to router behavior as a graceful restart helper";
        leaf admin-state {
          type srl_nokia-comm:admin-state;
          description
            "Administratively enable or disable graceful restart helper for all address families";
        }
        leaf stale-routes-time {
          type uint16 {
            range "1..3600";
          }
          units "seconds";
          description
            "The maximum number of seconds that routes received from a helped peer remain stale until they are deleted

             Routes of AFI/SAFI X received from peer Y are marked stale when peer Y goes down and its previous GR capability included AFI/SAFI X.";
        }
        leaf requested-restart-time {
          if-feature "srl_nokia-feat:bgp-graceful-restart-gaps";
          description
            "The restart time encoded in this router's GR capability.

             If the neighbor honors this request then this is the maximum time allowed for this router to re-establish its TCP connection after a restart. If this time is exceeded, the neighbor is expected to flush stale routes that it was maintaining on behalf of this router.";
          type uint16 {
            range "1..3600";
          }
          units "seconds";
          default "300";
        }
        leaf number-of-restarts {
          config false;
          type uint16;
          description
            "The number of times the peer has restarted";
        }
        leaf last-restart-time {
          config false;
          type srl_nokia-comm:date-and-time-delta;
          description
            "The last time the peer restarted";
        }
        leaf helper-active {
          config false;
          type boolean;
          description
            "Set to true when the router is actively helping the neighbor for at least one address family - i.e. for that address family the peer restarted with F=1 in its capability and the stale-routes-time has not expired yet";
        }
        container neighbor-capability {
          config false;
          description
            "Container for information about the last GR capability received from the neighbor";
          leaf restart-time {
            type uint16;
            description
              "The value of the Restart Time in the neighbor's last GR capability";
          }
          list afi-safi {
            description
              "List of AFI/SAFI TLVs that were contained in the neighbor's last GR capability";
            key "name";
            leaf name {
              type identityref {
                base srl_nokia-comm:bgp-address-family;
              }
            }
            leaf forwarding-preserved {
              type boolean;
              description
                "The F-bit setting in the AFI/SAFI TLV";
            }
          }
        }
      }
      container multihop {
        description
          "Configuration parameters specifying the multihop behaviour for an EBGP peer. This is not applicable to an IBGP peer.";
        leaf admin-state {
          type srl_nokia-comm:admin-state;
          description
            "When enabled, the peer is allowed to be indirectly connected by up to N hops, where N is controlled by the maximum-hops parameter. When disabled, multihop is allowed only if the peer type is IBGP.

             This overrides the group setting for admin-state.";
        }
        leaf maximum-hops {
          type uint8 {
            range "1..255";
          }
          description
            "This sets the maximum number of routing hops towards the peer. It determines the IP TTL value in originated BGP TCP/IP packets. By default the TTL is set to 1 towards an EBGP peer and 64 towards an IBGP peer.

             This overrides the group setting for maximum-hops.";
        }
      }
      uses optional-attributes-neighbor;
      list afi-safi {
        key "afi-safi-name";
        description
          "List of address families supported by the BGP neighbor";
        leaf afi-safi-name {
          type identityref {
            base srl_nokia-comm:bgp-address-family;
          }
          description
            "The name of a BGP address family, which translates to a specific AFI value and a specific SAFI value";
          must "not(. = 'evpn') or /srl_nokia-netinst:network-instance[srl_nokia-netinst:name = current()/../../../../../srl_nokia-netinst:name]/srl_nokia-netinst:type = 'srl_nokia-netinst:default'" {
            error-message "EVPN is not supported in network instances other than default";
          }
          must "not(. = 'l3vpn-ipv4-unicast') or /srl_nokia-netinst:network-instance[srl_nokia-netinst:name = current()/../../../../../srl_nokia-netinst:name]/srl_nokia-netinst:type = 'srl_nokia-netinst:default'" {
            error-message "L3VPN is not supported in network instances other than default";
          }
          must "not(. = 'l3vpn-ipv6-unicast') or /srl_nokia-netinst:network-instance[srl_nokia-netinst:name = current()/../../../../../srl_nokia-netinst:name]/srl_nokia-netinst:type = 'srl_nokia-netinst:default'" {
            error-message "L3VPN is not supported in network instances other than default";
          }
          must "not(. = 'ipv4-labeled-unicast') or /srl_nokia-netinst:network-instance[srl_nokia-netinst:name = current()/../../../../../srl_nokia-netinst:name]/srl_nokia-netinst:type = 'srl_nokia-netinst:default'" {
            error-message "Label-ipv4 is not supported in network instances other than default";
          }
          must "not(. = 'ipv6-labeled-unicast') or /srl_nokia-netinst:network-instance[srl_nokia-netinst:name = current()/../../../../../srl_nokia-netinst:name]/srl_nokia-netinst:type = 'srl_nokia-netinst:default'" {
            error-message "Label-ipv6 is not supported in network instances other than default";
          }
          must "not(. = 'route-target') or /srl_nokia-netinst:network-instance[srl_nokia-netinst:name = current()/../../../../../srl_nokia-netinst:name]/srl_nokia-netinst:type = 'srl_nokia-netinst:default'" {
            error-message "route-target is not supported in network instances other than default";
          }
          must "not(. = 'sr-policy-ipv4') or /srl_nokia-netinst:network-instance[srl_nokia-netinst:name = current()/../../../../../srl_nokia-netinst:name]/srl_nokia-netinst:type = 'srl_nokia-netinst:default'" {
            error-message "sr-policy-ipv4 is not supported in network instances other than default";
          }
          must "not(. = 'sr-policy-ipv6') or /srl_nokia-netinst:network-instance[srl_nokia-netinst:name = current()/../../../../../srl_nokia-netinst:name]/srl_nokia-netinst:type = 'srl_nokia-netinst:default'" {
            error-message "sr-policy-ipv6 is not supported in network instances other than default";
          }
        }
        leaf admin-state {
          type srl_nokia-comm:admin-state;
          description
            "This leaf indicates whether support for the AFI-SAFI is enabled/advertised to the neighbor";
        }
        leaf oper-state {
          config false;
          type enumeration {
            enum up {
              description
                "Negotiated operational state of the address family is up";
            }
            enum down {
              description
                "Negotiated operational state of the address family is down";
            }
          }
        }
        uses bgp-afi-safi-policy;
        container add-paths {
          if-feature "srl_nokia-feat:bgp-add-paths";
          description
            "Configure support for the advertisement and receipt of multiple paths for the AFI/SAFI";
          leaf receive {
            type boolean;
            description
              "Enable capability negotiation to receive multiple path advertisements from a single peer for a single NLRI belonging to the AFI/SAFI";
            must "../../afi-safi-name != 'ipv4-labeled-unicast'" {
              srl_nokia-ext:if-feature "not srl_nokia-feat:bgp-add-paths-labeled-unicast";
              error-message "add-paths is not supported for address familiy ipv4-labeled-unicast";
            }
            must "../../afi-safi-name != 'ipv6-labeled-unicast'" {
              srl_nokia-ext:if-feature "not srl_nokia-feat:bgp-add-paths-labeled-unicast";
              error-message "add-paths is not supported for address familiy ipv6-labeled-unicast";
            }
            must "../../afi-safi-name != 'l3vpn-ipv4-unicast'" {
              srl_nokia-ext:if-feature "not srl_nokia-feat:bgp-add-paths-l3vpn";
              error-message "add-paths is not supported for address familiy l3vpn-ipv4-unicast";
            }
            must "../../afi-safi-name != 'l3vpn-ipv6-unicast'" {
              srl_nokia-ext:if-feature "not srl_nokia-feat:bgp-add-paths-l3vpn";
              error-message "add-paths is not supported for address familiy l3vpn-ipv6-unicast";
            }
            must "../../afi-safi-name != 'evpn'" {
              srl_nokia-ext:if-feature "not srl_nokia-feat:bgp-add-paths-evpn";
              error-message "add-paths is not supported for address familiy evpn";
            }
            must "../../afi-safi-name != 'route-target'" {
              error-message "add-paths is not supported for address family route-target";
            }
            must "../../afi-safi-name != 'sr-policy-ipv4'" {
              error-message "add-paths is not supported for address family sr-policy-ipv4";
            }
            must "../../afi-safi-name != 'sr-policy-ipv6'" {
              error-message "add-paths is not supported for address family sr-policy-ipv6";
            }
          }
          leaf send {
            type boolean;
            description
              "Enable capability negotiation to send multiple path advertisements to a single peer for a single NLRI belonging to the AFI/SAFI";
            must "../../afi-safi-name != 'ipv4-labeled-unicast'" {
              srl_nokia-ext:if-feature "not srl_nokia-feat:bgp-add-paths-labeled-unicast";
              error-message "add-paths is not supported for address familiy ipv4-labeled-unicast";
            }
            must "../../afi-safi-name != 'ipv6-labeled-unicast'" {
              srl_nokia-ext:if-feature "not srl_nokia-feat:bgp-add-paths-labeled-unicast";
              error-message "add-paths is not supported for address familiy ipv6-labeled-unicast";
            }
            must "../../afi-safi-name != 'l3vpn-ipv4-unicast'" {
              srl_nokia-ext:if-feature "not srl_nokia-feat:bgp-add-paths-l3vpn";
              error-message "add-paths is not supported for address familiy l3vpn-ipv4-unicast";
            }
            must "../../afi-safi-name != 'l3vpn-ipv6-unicast'" {
              srl_nokia-ext:if-feature "not srl_nokia-feat:bgp-add-paths-l3vpn";
              error-message "add-paths is not supported for address familiy l3vpn-ipv6-unicast";
            }
            must "../../afi-safi-name != 'evpn'" {
              srl_nokia-ext:if-feature "not srl_nokia-feat:bgp-add-paths-evpn";
              error-message "add-paths is not supported for address familiy evpn";
            }
            must "../../afi-safi-name != 'route-target'" {
              error-message "add-paths is not supported for address family route-target";
            }
            must "../../afi-safi-name != 'sr-policy-ipv4'" {
              error-message "add-paths is not supported for address family sr-policy-ipv4";
            }
            must "../../afi-safi-name != 'sr-policy-ipv6'" {
              error-message "add-paths is not supported for address family sr-policy-ipv6";
            }
          }
          choice selection-algorithm {
            leaf send-max {
              type uint8 {
                range "1..16";
              }
              description
                "Send the N best paths for a single NLRI, or as many as possible until there are no more valid paths to send.

                 This ensures the best path is advertised but does not limit the additional paths to being 'used' paths.";
              must '../send = true()' {
                error-message "send capability must be advertised";
              }
            }
            leaf send-multipath {
              type empty;
              description
                "Send the used paths for a single NLRI, including all paths that are multipaths.";
              must '../send = true()' {
                error-message "send capability must be advertised";
              }
            }
          }
        }
        leaf received-routes {
          config false;
          type uint32;
          description
            "The number of routes belonging to this AFI/SAFI received from the peer, including routes rejected by import policy";
        }
        leaf sent-routes {
          config false;
          type uint32;
          description
            "The number of routes belonging to this AFI/SAFI advertised as reachable to the peer";
        }
        leaf active-routes {
          config false;
          type uint32;
          description
            "The number of routes belonging to this AFI/SAFI received from the peer that are installed and used, being best routes";
        }
        leaf rejected-routes {
          config false;
          type uint32;
          description
            "The number of routes belonging to this AFI/SAFI received from the peer that were rejected by import policy";
        }
        leaf suppressed-routes {
          if-feature "srl_nokia-feat:bgp-route-flap-damping";
          config false;
          type uint32;
          description
            "The number of routes belonging to this AFI/SAFI received from the peer that are suppressed because their route-flap-damping FOM is greater than the suppress-threshold";
        }
        leaf received-routes-withdrawn-due-to-error {
          config false;
          type uint32;
          description
            "The number of routes belonging to this AFI/SAFI received from the peer that were withdrawn due to an update packet error";
        }
        container ipv4-unicast {
          description
            "Options related to the IPv4-unicast address family";
          uses rfc-8950-group-neighbor;
          container prefix-limit-received {
            description
              "Options for configuring the maximum number of IPv4 routes allowed to be received from the peer";
            leaf max-received-routes {
              type uint32 {
                range "1..4294967295";
              }
              description
                "Maximum number of IPv4 routes that will be accepted from the neighbor, counting routes accepted and rejected by import policies";
              must "../../../afi-safi-name = 'ipv4-unicast'" {
                error-message "Only allowed on afi-safi ipv4-unicast";
              }
            }
            leaf warning-threshold-pct {
              type percentage;
              description
                "When the number of IPv4 routes received from the peer (counting routes accepted and rejected by import policy) reaches this percentage of the max-received-routes limit, BGP raises a warning log event";
              must "../../../afi-safi-name = 'ipv4-unicast'" {
                error-message "Only allowed on afi-safi ipv4-unicast";
              }
            }
            leaf prevent-teardown {
              if-feature "srl_nokia-feat:bgp-prefix-limit";
              type boolean;
              description
                "When false the session is immediately torn down when the number of received IPv4 routes exceeds the configured limit.";
              must "../../../afi-safi-name = 'ipv4-unicast'" {
                error-message "Only allowed on afi-safi ipv4-unicast";
              }
            }
            leaf prefix-limit-exceeded {
              if-feature "srl_nokia-feat:bgp-prefix-limit";
              config false;
              type boolean;
              description
                "Changes from false to true when the number of received IPv4 routes increases to max-received-routes + 1 and remains true until the number of received IPv4 routes decreases back to max-received-routes (applicable if prevent-teardown = true) or until the session is re-established (applicable if prevent-teardown = false)";
            }
          }
          uses link-bandwidth;
        }
        container ipv4-labeled-unicast {
          if-feature "srl_nokia-feat:bgp-labeled-unicast";
          description
            "Options related to the labeled IPv4-unicast address family";
          uses rfc-8950-group-neighbor {
            if-feature "srl_nokia-feat:bgp-labeled-unicast-future";
          }
          leaf next-hop-unchanged {
            if-feature "srl_nokia-feat:bgp-labeled-unicast-future";
            type boolean;
            description
              "When set to true, do not change the BGP next-hop towards group peers, even if next-hop-self is normally performed";
            must "../../afi-safi-name = 'ipv4-labeled-unicast'" {
              error-message "Only allowed with afi-safi ipv4-labeled-unicast";
            }
          }
          container prefix-limit-received {
            if-feature "srl_nokia-feat:bgp-labeled-unicast-future";
            description
              "Options for configuring the maximum number of label-IPv4 routes allowed to be received from the peer";
            leaf max-received-routes {
              type uint32 {
                range "1..4294967295";
              }
              description
                "Maximum number of label-IPv4 routes that will be accepted from the neighbor, counting routes accepted and rejected by import policies";
              must "../../../afi-safi-name = 'ipv4-labeled-unicast'" {
                error-message "Only allowed with afi-safi ipv4-labeled-unicast";
              }
            }
            leaf warning-threshold-pct {
              type percentage;
              description
                "When the number of label-IPv4 routes received from the peer (counting routes accepted and rejected by import policy) reaches this percentage of the max-received-routes limit, BGP raises a warning log event";
              must "../../../afi-safi-name = 'ipv4-labeled-unicast'" {
                error-message "Only allowed with afi-safi ipv4-labeled-unicast";
              }
            }
            leaf prevent-teardown {
              type boolean;
              description
                "When false the session is immediately torn down when the number of received label-IPv4 routes exceeds the configured limit.";
              must "../../../afi-safi-name = 'ipv4-labeled-unicast'" {
                error-message "Only allowed with afi-safi ipv4-labeled-unicast";
              }
            }
            leaf prefix-limit-exceeded {
              config false;
              type boolean;
              description
                "Changes from false to true when the number of received label-IPv4 routes increases to max-received-routes + 1 and remains true until the number of received label-IPv4 routes decreases back to max-received-routes (applicable if prevent-teardown = true) or until the session is re-established (applicable if prevent-teardown = false)";
            }
          }
        }
        container l3vpn-ipv4-unicast {
          if-feature "srl_nokia-feat:inter-as-nhsrr-ipvpn or srl_nokia-feat:ipvpn";
          description
            "Options related to the VPN-IPv4 unicast address family";
          uses rfc-8950-group-neighbor;
          container prefix-limit-received {
            description
              "Options for configuring the maximum number of VPN-IPv4 unicast routes allowed to be received from the peer";
            leaf max-received-routes {
              type uint32 {
                range "1..4294967295";
              }
              description
                "Maximum number of VPN-IPv4 routes that will be accepted from the neighbor, counting routes accepted and rejected by import policies";
              must "../../../afi-safi-name = 'l3vpn-ipv4-unicast'" {
                error-message "Only allowed on afi-safi l3vpn-ipv4-unicast";
              }
            }
            leaf warning-threshold-pct {
              type percentage;
              description
                "When the number of VPN-IPv4 routes received from the peer (counting routes accepted and rejected by import policy) reaches this percentage of the max-received-routes limit, BGP raises a warning log event";
              must "../../../afi-safi-name = 'l3vpn-ipv4-unicast'" {
                error-message "Only allowed on afi-safi l3vpn-ipv4-unicast";
              }
            }
            leaf prevent-teardown {
              type boolean;
              description
                "When false the session is immediately torn down when the number of received VPN-IPv4 routes exceeds the configured limit.";
              must "../../../afi-safi-name = 'l3vpn-ipv4-unicast'" {
                error-message "Only allowed on afi-safi l3vpn-ipv4-unicast";
              }
            }
            leaf prefix-limit-exceeded {
              config false;
              type boolean;
              description
                "Changes from false to true when the number of received VPN-IPv4 routes increases to max-received-routes + 1 and remains true until the number of received VPN-IPv4 routes decreases back to max-received-routes (applicable if prevent-teardown = true) or until the session is re-established (applicable if prevent-teardown = false)";
            }
          }
        }
        container ipv6-unicast {
          description
            "Options related to the IPv6-unicast address family";
          container prefix-limit-received {
            description
              "Options for configuring the maximum number of IPv6 routes allowed to be received from the peer";
            leaf max-received-routes {
              type uint32 {
                range "1..4294967295";
              }
              description
                "Maximum number of IPv6 routes that will be accepted from the neighbor, counting routes accepted and rejected by import policies";
              must "../../../afi-safi-name = 'ipv6-unicast'" {
                error-message "Only allowed on afi-safi ipv6-unicast";
              }
            }
            leaf warning-threshold-pct {
              type percentage;
              description
                "When the number of IPv6 routes received from the peer (counting routes accepted and rejected by import policy) reaches this percentage of the max-received-routes limit, BGP raises a warning log event";
              must "../../../afi-safi-name = 'ipv6-unicast'" {
                error-message "Only allowed on afi-safi ipv6-unicast";
              }
            }
            leaf prevent-teardown {
              if-feature "srl_nokia-feat:bgp-prefix-limit";
              type boolean;
              description
                "When false the session is immediately torn down when the number of received IPv6 routes exceeds the configured limit.";
              must "../../../afi-safi-name = 'ipv6-unicast'" {
                error-message "Only allowed on afi-safi ipv6-unicast";
              }
            }
            leaf prefix-limit-exceeded {
              if-feature "srl_nokia-feat:bgp-prefix-limit";
              config false;
              type boolean;
              description
                "Changes from false to true when the number of received IPv6 routes increases to max-received-routes + 1 and remains true until the number of received IPv6 routes decreases back to max-received-routes      (applicable if prevent-teardown = true) or until the session is re-established (applicable if prevent-teardown = false)";
            }
          }
          uses link-bandwidth;
        }
        container ipv6-labeled-unicast {
          if-feature "srl_nokia-feat:bgp-labeled-unicast";
          description
            "Options related to the labeled-IPv6-unicast address family";
          leaf next-hop-unchanged {
            if-feature "srl_nokia-feat:bgp-labeled-unicast-future";
            type boolean;
            description
              "When set to true, do not change the BGP next-hop towards group peers, even if next-hop-self is normally performed";
            must "../../afi-safi-name = 'ipv6-labeled-unicast'" {
              error-message "Only allowed with afi-safi ipv6-labeled-unicast";
            }
          }
          container prefix-limit-received {
            if-feature "srl_nokia-feat:bgp-labeled-unicast-future";
            description
              "Options for configuring the maximum number of label-IPv6 routes allowed to be received from the peer";
            leaf max-received-routes {
              type uint32 {
                range "1..4294967295";
              }
              description
                "Maximum number of label-IPv6 routes that will be accepted from the neighbor, counting routes accepted and rejected by import policies";
              must "../../../afi-safi-name = 'ipv6-labeled-unicast'" {
                error-message "Only allowed with afi-safi ipv6-labeled-unicast";
              }
            }
            leaf warning-threshold-pct {
              type percentage;
              description
                "When the number of label-IPv6 routes received from the peer (counting routes accepted and rejected by import policy) reaches this percentage of the max-received-routes limit, BGP raises a warning log event";
              must "../../../afi-safi-name = 'ipv6-labeled-unicast'" {
                error-message "Only allowed with afi-safi ipv6-labeled-unicast";
              }
            }
            leaf prevent-teardown {
              type boolean;
              description
                "When false the session is immediately torn down when the number of received label-IPv6 routes exceeds the configured limit.";
              must "../../../afi-safi-name = 'ipv6-labeled-unicast'" {
                error-message "Only allowed with afi-safi ipv6-labeled-unicast";
              }
            }
            leaf prefix-limit-exceeded {
              config false;
              type boolean;
              description
                "Changes from false to true when the number of received label-IPv6 routes increases to max-received-routes + 1 and remains true until the number of received label-IPv6 routes decreases back to max-received-routes (applicable if prevent-teardown = true) or until the session is re-established (applicable if prevent-teardown = false)";
            }
          }
        }
        container l3vpn-ipv6-unicast {
          if-feature "srl_nokia-feat:inter-as-nhsrr-ipvpn or srl_nokia-feat:ipvpn";
          description
            "Options related to the VPN-IPv6 unicast address family";
          container prefix-limit-received {
            description
              "Options for configuring the maximum number of VPN-IPv6 unicast routes allowed to be received from the peer";
            leaf max-received-routes {
              type uint32 {
                range "1..4294967295";
              }
              description
                "Maximum number of VPN-IPv6 routes that will be accepted from the neighbor, counting routes accepted and rejected by import policies";
              must "../../../afi-safi-name = 'l3vpn-ipv6-unicast'" {
                error-message "Only allowed on afi-safi l3vpn-ipv6-unicast";
              }
            }
            leaf warning-threshold-pct {
              type percentage;
              description
                "When the number of VPN-IPv6 routes received from the peer (counting routes accepted and rejected by import policy) reaches this percentage of the max-received-routes limit, BGP raises a warning log event";
              must "../../../afi-safi-name = 'l3vpn-ipv6-unicast'" {
                error-message "Only allowed on afi-safi l3vpn-ipv6-unicast";
              }
            }
            leaf prevent-teardown {
              type boolean;
              description
                "When false the session is immediately torn down when the number of received VPN-IPv6 routes exceeds the configured limit.";
              must "../../../afi-safi-name = 'l3vpn-ipv6-unicast'" {
                error-message "Only allowed on afi-safi l3vpn-ipv6-unicast";
              }
            }
            leaf prefix-limit-exceeded {
              config false;
              type boolean;
              description
                "Changes from false to true when the number of received VPN-IPv6 routes increases to max-received-routes + 1 and remains true until the number of received VPN-IPv6 routes decreases back to max-received-routes (applicable if prevent-teardown = true) or until the session is re-established (applicable if prevent-teardown = false)";
            }
          }
        }
        container evpn {
          description
            "Options related to the EVPN address family";
          leaf advertise-ipv6-next-hops {
            type boolean;
            must "/srl_nokia-netinst:network-instance[srl_nokia-netinst:name = current()/../../../../../../srl_nokia-netinst:name]/srl_nokia-netinst:type = 'srl_nokia-netinst:default'" {
              error-message "EVPN is not supported in network instances other than default";
            }
            description
              "Enables advertisement of EVPN routes with IPv6 next-hops to peers

               If this is set to true and the local-address used towards the peer is an IPv6 address and BGP is supposed to apply next-hop-self then the route is advertised with the IPv6 local-address as the BGP next-hop. If this is set to false, then the EVPN route is advertised with an IPv4 next-hop.";
          }
          container prefix-limit-received {
            description
              "Options for configuring the maximum number of EVPN routes allowed to be received from the peer";
            leaf max-received-routes {
              type uint32 {
                range "1..4294967295";
              }
              must "/srl_nokia-netinst:network-instance[srl_nokia-netinst:name = current()/../../../../../../../srl_nokia-netinst:name]/srl_nokia-netinst:type = 'srl_nokia-netinst:default'" {
                error-message "EVPN is not supported in network instances other than default";
              }
              must "../../../afi-safi-name = 'evpn'" {
                error-message "Only allowed on afi-safi evpn";
              }
              description
                "Maximum number of EVPN routes that will be accepted from the neighbor, counting routes accepted and rejected by import policies";
            }
            leaf warning-threshold-pct {
              type percentage;
              must "/srl_nokia-netinst:network-instance[srl_nokia-netinst:name = current()/../../../../../../../srl_nokia-netinst:name]/srl_nokia-netinst:type = 'srl_nokia-netinst:default'" {
                error-message "EVPN is not supported in network instances other than default";
              }
              description
                "When the number of EVPN routes received from the peer (counting routes accepted and rejected by import policy) reaches this percentage of the max-received-routes limit, BGP raises a warning log event";
              must "../../../afi-safi-name = 'evpn'" {
                error-message "Only allowed on afi-safi evpn";
              }
            }
          }
          leaf default-received-encapsulation {
            if-feature "srl_nokia-feat:nhsrr-evpn";
            type enumeration {
              enum vxlan {
                value 1;
              }
              enum mpls {
                value 2;
              }
            }
            description
              "Indicates the encapsulation considered when the routes are received without BGP encapsulation extended community

               Most EVPN routes are usually received with a BGP encapsulation extended community that indicates the encapsulation
               and therefore how to interpret the value in the received Label fields of the routes. If no encapsulation is
               received, BGP will validate the route as MPLS or VXLAN or SRv6 depending on how this command is configured.";
          }
        }
        container route-target {
          if-feature "srl_nokia-feat:bgp-rtc";
          description
            "Options related to the RT constraint address family";
          leaf send-default-route {
            type boolean;
            description
              "When true the router advertises a synthetically generated default RTC route to the neighbor";
          }
          container prefix-limit-received {
            description
              "Options for configuring the maximum number of RTC routes allowed to be received from the peer";
            leaf max-received-routes {
              type uint32 {
                range "1..4294967295";
              }
              must "/srl_nokia-netinst:network-instance[srl_nokia-netinst:name = current()/../../../../../../../srl_nokia-netinst:name]/srl_nokia-netinst:type = 'srl_nokia-netinst:default'" {
                error-message "RTC is not supported in network instances other than default";
              }
              description
                "Maximum number of RTC routes that will be accepted from the neighbor, counting routes accepted and rejected by import policies";
            }
            leaf warning-threshold-pct {
              type percentage;
              must "/srl_nokia-netinst:network-instance[srl_nokia-netinst:name = current()/../../../../../../../srl_nokia-netinst:name]/srl_nokia-netinst:type = 'srl_nokia-netinst:default'" {
                error-message "RTC is not supported in network instances other than default";
              }
              description
                "When the number of RTC routes received from the peer (counting routes accepted and rejected by import policy) reaches this percentage of the max-received-routes limit, BGP raises a warning log event";
            }
            leaf prevent-teardown {
              type boolean;
              description
                "When false the session is immediately torn down when the number of received RTC routes exceeds the configured limit.";
            }
            leaf prefix-limit-exceeded {
              config false;
              type boolean;
              description
                "Changes from false to true when the number of received routes increases to max-received-routes + 1 and remains true until the number of received routes decreases back to max-received-routes (applicable if prevent-teardown = true) or until the session is re-established (applicable if prevent-teardown = false)";
            }
          }
        }
      }
      container local-as {
        description
          "Options related to the local autonomous-system number advertised by this router to the peer";
        leaf as-number {
          type srl_nokia-comm:as-number;
          description
            "The local autonomous system number used to override the global ASN on this session

             Sets the ASN value that this router sends in its OPEN message towards its peer.";
        }
        leaf prepend-global-as {
          type boolean;
          description
            "When set to true, the global ASN value is prepended to the AS path in outbound routes towards the peer

             If a session is EBGP (peer-as is not equal to the local-as) then the local-as is prepended as the final step, so that the local-as is the first element in the AS_PATH received by the peer.";
          must '../as-number' {
            error-message "must have as-number to set prepend-global-as";
          }
        }
        leaf prepend-local-as {
          type boolean;
          description
            "When set to true, the local AS value is prepended to the AS path of inbound routes from the peer";
          must '../as-number' {
            error-message "must have as-number to set prepend-local-as";
          }
        }
      }
      leaf route-flap-damping {
        if-feature "srl_nokia-feat:bgp-route-flap-damping";
        description
          "Enable/disable route flap damping procedures for routes received from this peer if it is an EBGP peer

           If no value is configured, the setting is inherited from the peer-group to which the peer belongs.

           The configured or omherited setting has no effect if the peer is IBGP.";
        type boolean;
      }
      container route-reflector {
        description
          "Container with route reflection configuration options.";
        leaf client {
          description
            "When this is set to true this BGP session is considered an RR client.";
          type boolean;
        }
        leaf cluster-id {
          description
            "The cluster-id to insert into the CLUSTER_LIST attribute when reflecting routes received by or sent to this client. The default is inherited from group or instance level configuration.";
          type cluster-id-type;
        }
      }
      container send-community {
        description
          "Options for controlling the sending of BGP communities to the peer";
        leaf standard {
          type boolean;
          description
            "The false setting causes BGP to strip all standard (4 byte) communities from all outbound routes advertised to the peer";
        }
        leaf large {
          type boolean;
          description
            "The false setting causes BGP to strip all large (12 byte) BGP communities from all outbound routes advertised to the peer";
        }
      }
      container send-default-route {
        description
          "Options for controlling the generation of default routes towards the peer";
        leaf ipv4-unicast {
          type boolean;
          description
            "Enables the sending of a synthetically generated default IPv4 route [0/0] to the peer";
        }
        leaf ipv6-unicast {
          type boolean;
          description
            "Enables the sending of a synthetically generated default IPv6 route [::/0] to the peer";
        }
        leaf export-policy {
          type leafref {
            path "/srl-rpol:routing-policy/srl-rpol:policy/srl-rpol:name";
          }
          description
            "The name of a policy that should be applied to the advertised default routes, in order to set their attributes to non-default values

             Only the default-action of this policy is parsed and applied.";
        }
      }
      container timers {
        leaf connect-retry {
          type uint16 {
            range "1..65535";
          }
          units "seconds";
          description
            "The time interval in seconds between successive attempts to establish a session with a peer";
        }
        leaf hold-time {
          type uint16 {
            range "0|3..65535";
          }
          units "seconds";
          description
            "The hold-time interval in seconds that the router proposes to the peer in its OPEN message

             The actual in-use hold-time is negotiated to the lowest value proposed by the two peers. A negotiated value of 0 suppresses the sending of keepalives by both peers.";
        }
        leaf keepalive-interval {
          type uint16 {
            range "0..21845";
          }
          units "seconds";
          description
            "The interval in seconds between successive keepalive messages sent to the peer

             The period between one keepalive message and the next is the minimum of this configured (or inherited) value and 1/3 of the negotiated hold-time duration. A value of 0 suppresses the sending of keepalives to the peer.";
        }
        leaf minimum-advertisement-interval {
          type uint16 {
            range "1..255";
          }
          units "seconds";
          description
            "The value assigned to the MinRouteAdvertisementIntervalTimer of RFC 4271, for both EBGP and IBGP sessions

             Each session runs its own independent timer and the timer affects both route advertisements and route withdrawals, regardless of address family. For route withdrawals only, this timer is bypassed if rapid-withdrawal is set to true.";
        }
        leaf prefix-limit-restart-timer {
          if-feature "srl_nokia-feat:bgp-prefix-limit";
          type uint16;
          units "seconds";
          description
            "Time interval in seconds after which the BGP session is re-established after being torn down due to exceeding any prefix limit (of any address family)

             This only applies if prevent-teardown is false.";
        }
        leaf next-connect-retry-time {
          config false;
          type srl_nokia-comm:date-and-time-delta;
          description
            "The time when the next connect retry attempt will occur";
        }
        leaf negotiated-hold-time {
          config false;
          type uint16;
          description
            "The operational hold-time

             It is negotiated to the lowest value proposed by the two peers. A negotiated value of 0 suppresses the sending of keepalives by both peers.";
        }
        leaf negotiated-keepalive-interval {
          config false;
          description
            "The operational keepalive interval

             It is the minimum of the configured value and 1/3 of the negotiated-hold-time. A value of 0 suppresses the sending of keepalives to the peer.";
          type uint16;
        }
      }
      uses traceoptions;
      container transport {
        leaf mtu-discovery {
          if-feature "srl_nokia-feat:bgp-mtu-discovery";
          type boolean;
          description
            "Turns path mtu discovery on (true) or off (false)";
        }
        leaf tcp-mss {
          type uint16 {
            range "536..9446";
          }
          units "bytes";
          description
            "The maximum segment size of BGP TCP packets

             The configured value of this leaf is the TCP MSS value advertised to the peer during TCP connection setup (in the TCP MSS option), reduced if necessary to accommodate the outgoing interface IP MTU.
             The state value of this leaf is the operational TCP MSS used in the data transmit direction towards the peer. It may be less than the received TCP MSS option value due to adjustment for TCP options used in the transit direction and/or the path MTU discovery process (if enabled).";
        }
        leaf passive-mode {
          type boolean;
          description
            "The true setting causes BGP to wait for the peer to initiate the TCP connection

             The false setting causes BGP to initiate a TCP connection whenever the BGP session is started or restarted.";
        }
        leaf local-address {
          type union {
            type srl_nokia-comm:ip-address;
            type srl_nokia-comm:subinterface-all;
          }
          description
            "The local TCP endpoint of used for the BGP session

             This also the source address for next-hop-self, if it applies. The local-address can be specified as an IP address that is resolvable to a local interface.

             This address must be the primary address of an interface, otherwise the session will not come up.";
        }
        leaf local-port {
          config false;
          type uint16;
          description
            "Local TCP port used for the TCP connection to the peer";
        }
        leaf remote-port {
          config false;
          type uint16;
          description
            "Remote TCP port used by the peer for its TCP connection to the local router";
        }
      }
      uses neighbor-state;
    }
  }

  grouping convergence-for-family {
    container convergence {
      description
        "Options for controlling and monitoring routing convergence of the relevant address family";
      leaf max-wait-to-advertise {
        type uint16 {
          range "0..3600";
        }
        default "0";
        must '(. = 0) or (. >= ../../../../convergence/min-wait-to-advertise)' {
          error-message "Invalid max-wait-to-advertise value. Value should be greater than or equal to min-wait-to-advertise.";
        }
        description
          "The maximum amount of time, in seconds, measured from the time when the first session (configured or dynamic) that supports the address family comes up after a BGP restart, until BGP is allowed to advertise any routes in that address family to any peer

           The value of this leaf must always be greater than or equal to the operational value of min-wait-to-advertise. The default value is 3x the value of min-wait-to-advertise. A value of 0 means the feature is disabled and there is no additional delay before advertising routes of the address family.";
      }
      leaf oper-max-wait-to-advertise {
        config false;
        type uint16 {
          range "0..10800";
        }
        description
          "The operational value of the max-wait-to-advertise timer for the address family";
      }
      leaf up-peers-when-min-expired {
        config false;
        type uint16;
        description
          "The number of BGP sessions (configured and dynamic) that support the address family and that were in established state when the win-wait-to-advertise timer expired";
      }
      leaf up-peers {
        config false;
        type uint16;
        description
          "The number of BGP sessions (configured and dynamic) that support the address family and that are currently in the established state";
      }
      leaf converged-peers {
        config false;
        type uint16;
        description
          "The number of peers that have sent an EOR marker for the address family since the last BGP restart";
      }
      leaf first-up-peer-time {
        config false;
        type srl_nokia-comm:timeticks64;
        description
          "The time when the first session supporting the address family came up, measured from the time that the BGP instance restarted";
      }
      leaf last-up-peer-time {
        config false;
        type srl_nokia-comm:timeticks64;
        description
          "The time when the last session supporting the address family came up, measured from the time that the BGP instance restarted";
      }
      leaf convergence-state {
        config false;
        type enumeration {
          enum waiting {
            description
              "BGP has recently restarted and no sessions have re-established yet";
          }
          enum started {
            description
              "BGP has recently restarted and at least one session has re-established with support of the address family";
          }
          enum partial {
            description
              "BGP has recently restarted and at least one session has advertised an End-of-RIB marker for the address family.";
          }
          enum timeout {
            description
              "BGP has recently restarted and not all non-slow peers advertised an End-of-RIB marker for the address family before the max-wait-to-advertise timer expired";
          }
          enum converged {
            description
              "All non-slow peers that support the address family have have advertised the End-of-RIB marker for the address family";
          }
        }
      }
      leaf convergence-time {
        config false;
        type srl_nokia-comm:timeticks64;
        description
          "The elapsed time in seconds, starting from the last BGP restart, to reach the converged state for the address family";
      }
    }
  }

  grouping entropy-label {
    container entropy-label {
      if-feature "srl_nokia-feat:entropy-bgp-sr";
      description
        "Options for configuring control and data plane aspects of entropy label";
      leaf transmit {
        description
          "Specify conditions for adding ELI/EL when pushing BGP label";
        type enumeration {
          enum enable;
          enum disable;
        }
        default "disable";
        must ". = 'disable' or current()/../../../../../../srl_nokia-netinst:type = 'srl_nokia-netinst:default'" {
          error-message "entropy-label is not supported in network instance other than default";
        }
      }
    }
  }

  grouping multipath-family-config {
    container multipath {
      description
        "Options related to BGP multipath";
      leaf allow-multiple-as {
        type boolean;
        default "true";
        description
          "When set to true, BGP is allowed to build a multipath set using BGP routes with different neighbor AS (most recent AS in the AS_PATH)

           When set to false, BGP is only allowed to use non-best paths for ECMP if they meet the multipath criteria and they have the same neighbor AS as the best path";
      }
      leaf maximum-paths {
        if-feature "srl_nokia-feat:bgp-multipath-maximum-paths";
        type ip-ecmp;
        default "1";
        description
          "The maximum number of BGP ECMP next-hops for BGP routes with an NLRI belonging to the address family of this configuration context";
        must '. <= 64' {
          error-message "Valid range for maximum-paths:[1..64] ";
          srl_nokia-ext:if-feature "not (srl_nokia-feat:bgp-multipath-maximum-paths-limit-128 or srl_nokia-feat:bgp-multipath-maximum-paths-limit-256)";
        }
        must "../../afi-safi-name = 'ipv4-unicast' or ../../afi-safi-name = 'ipv6-unicast' or . <= 64" {
          error-message "Valid range for maximum-paths:[1..64] ";
          srl_nokia-ext:if-feature "srl_nokia-feat:bgp-multipath-maximum-paths-limit-128 or srl_nokia-feat:bgp-multipath-maximum-paths-limit-256";
        }
        must "not (../../afi-safi-name = 'ipv4-unicast' or ../../afi-safi-name = 'ipv6-unicast') or . <= 128" {
          error-message "Valid range for maximum-paths:[1..128] ";
          srl_nokia-ext:if-feature "srl_nokia-feat:bgp-multipath-maximum-paths-limit-128";
        }
        must "not (../../afi-safi-name = 'ipv4-unicast' or ../../afi-safi-name = 'ipv6-unicast') or . <= 256" {
          error-message "Valid range for maximum-paths:[1..256] ";
          srl_nokia-ext:if-feature "srl_nokia-feat:bgp-multipath-maximum-paths-limit-256";
        }
        must '(. <= 8)' {
          srl_nokia-ext:if-feature "srl_nokia-features:platform-7215-a1";
          error-message "Value cannot be greater than 8 on the 7215 IXS-A1 platform.";
        }
      }
    }
  }

  grouping weighted-ecmp-family-config {
    container weighted-ecmp {
      if-feature "srl_nokia-feat:bgp-weighted-ecmp";
      description
        "Weighted-ecmp for the AFI/SAFI";
      leaf admin-state {
        type srl_nokia-comm:admin-state;
        description
          "Admin-state for weighted-ecmp for the AFI/SAFI";
        must "../../afi-safi-name = 'ipv4-unicast' or ../../afi-safi-name = 'ipv6-unicast'" {
          error-message "weighted-ecmp is not supported for address families other than IPv4 unicast and IPv6 unicast";
        }
      }
    }
  }

  grouping backup-paths-family-config {
    container backup-paths {
      description
        "Configure backup paths support for the AFI/SAFI";
      leaf install {
        description
          "Install a backup path for every NLRI in the address family, when a suitable one exists";
        type boolean;
        default "false";
      }
    }
  }

  grouping color-aware-next-hop-resolution {
    container color-aware {
      description
        "Color-aware next-hop resolution options";
      container tag {
        if-feature "srl_nokia-feat:bgp-next-hop-resolution-tag";
        description
          "Next-hop resolution constraints based on internal tags";
        leaf mandatory {
          description
            "If true, a tunnel can resolve the next-hop only if it has all the same tags as the route

             If false, it is possible to select a tunnel that has none or only some of the same tags as the route.";
          type boolean;
          default "false";
        }
      }
    }
  }

  grouping allowed-tunnel-types-unlabeled {
    leaf-list allowed-tunnel-types {
      description
        "List of allowed tunnel types";
      type identityref {
        base srl_nokia-comm:bgp-next-hop-resolution-tunnel-type;
      }
      must "not(. = 'te-policy-sr-mpls-colored')" {
        srl_nokia-ext:if-feature "not srl_nokia-feat:future-0-0";
        error-message "unsupported resolving tunnel";
      }
      must "not(. = 'bgp')" {
        srl_nokia-ext:if-feature "not srl_nokia-feat:bgp-labeled-unicast";
        error-message "unsupported resolving tunnel";
      }
    }
  }

  grouping next-hop-resolution-unlabeled {
    container next-hop-resolution {
      if-feature "srl_nokia-feat:mpls";
      description
        "Options for controlling next-hop resolution procedures";
      container ipv4-next-hops {
        description
          "Options related to the resolution of BGP next-hops that are IPv4 addresses";
        container tunnel-resolution {
          description
            "Options related to resolution using tunnels in the tunnel table";
          leaf mode {
            description
              "Mode to control the order of tunnel resolution compared to route resolution";
            type enumeration {
              enum prefer;
              enum require;
              enum disabled;
            }
            default "disabled";
          }
          uses allowed-tunnel-types-unlabeled;
          uses color-aware-next-hop-resolution {
            if-feature "srl_nokia-feat:bgp-next-hop-resolution-tag or srl_nokia-feat:isis-flex-algo or srl_nokia-feat:segment-routing-colored-te-policies";
          }
        }
      }
      container ipv6-next-hops {
        if-feature "srl_nokia-feat:bgp-ipv6-next-hop-tunnel-resolution";
        description
          "Options related to the resolution of BGP next-hops that are IPv6 addresses";
        container tunnel-resolution {
          description
            "Options related to resolution using tunnels in the tunnel table";
          leaf mode {
            description
              "Mode to control the order of tunnel resolution compared to route resolution";
            type enumeration {
              enum prefer;
              enum require;
              enum disabled;
            }
            default "disabled";
          }
          uses allowed-tunnel-types-unlabeled;
          uses color-aware-next-hop-resolution {
            if-feature "srl_nokia-feat:bgp-next-hop-resolution-tag or srl_nokia-feat:isis-flex-algo or srl_nokia-feat:segment-routing-colored-te-policies";
          }
        }
      }
    }
  }

  grouping allowed-tunnel-types-labeled {
    leaf-list allowed-tunnel-types {
      description
        "List of allowed tunnel types";
      type identityref {
        base srl_nokia-comm:bgp-next-hop-resolution-tunnel-type;
      }
      must "not(. = 'bgp')" {
        error-message "unsupported resolving tunnel";
      }
      must "not(. = 'te-policy-sr-mpls-uncolored')" {
        srl_nokia-ext:if-feature "not srl_nokia-feat:bgp-labeled-unicast-over-sr-te";
        error-message "unsupported resolving tunnel";
      }
    }
  }

  grouping next-hop-resolution-labeled {
    container next-hop-resolution {
      description
        "Options for controlling next-hop resolution procedures";
      container ipv4-next-hops {
        description
          "Options related to the resolution of BGP next-hops that are IPv4 addresses";
        container route-resolution {
          description
            "Options related to resolution using IP routes in the FIB";
          leaf admin-state {
            description
              "Enable or disable route resolution if no resolving tunnel is found";
            type srl_nokia-comm:admin-state;
            default "enable";
          }
          leaf ignore-default-routes {
            description
              "Ignore default routes, regardless of route type";
            type boolean;
            default "true";
          }
        }
        container tunnel-resolution {
          description
            "Options related to resolution using tunnels in the tunnel table";
          uses allowed-tunnel-types-labeled;
          uses color-aware-next-hop-resolution {
            if-feature "(srl_nokia-feat:bgp-next-hop-resolution-tag and srl_nokia-feat:bgp-labeled-unicast-over-sr-te) or srl_nokia-feat:isis-flex-algo or srl_nokia-feat:segment-routing-colored-te-policies";
          }
        }
      }
      container ipv6-next-hops {
        description
          "Options related to the resolution of BGP next-hops that are IPv6 addresses";
        container route-resolution {
          description
            "Options related to resolution using IP routes in the FIB";
          leaf admin-state {
            description
              "Enable or disable route resolution if no resolving tunnel is found";
            type srl_nokia-comm:admin-state;
            default "enable";
          }
          leaf ignore-default-routes {
            description
              "Ignore default routes, regardless of route type";
            type boolean;
            default "true";
          }
        }
        container tunnel-resolution {
          description
            "Options related to resolution using tunnels in the tunnel table";
          uses allowed-tunnel-types-labeled;
          uses color-aware-next-hop-resolution {
            if-feature "(srl_nokia-feat:bgp-next-hop-resolution-tag and srl_nokia-feat:bgp-labeled-unicast-over-sr-te) or srl_nokia-feat:isis-flex-algo or srl_nokia-feat:segment-routing-colored-te-policies";
          }
        }
      }
    }
  }

  grouping allowed-tunnel-types-evpn-ipvpn-mpls {
    leaf-list allowed-tunnel-types {
      description
        "List of allowed tunnel types";
      type identityref {
        base srl_nokia-comm:bgp-next-hop-resolution-tunnel-type;
      }
    }
  }

  grouping next-hop-resolution-evpn-ipvpn-mpls {
    container next-hop-resolution {
      description
        "Options for controlling next-hop resolution procedures";
      container ipv4-next-hops {
        description
          "Options related to the resolution of BGP next-hops that are IPv4 addresses";
        container route-resolution {
          description
            "Options related to resolution using IP routes in the FIB";
          leaf admin-state {
            description
              "Enable or disable route resolution if no resolving tunnel is found";
            type srl_nokia-comm:admin-state;
            default "enable";
          }
          leaf ignore-default-routes {
            description
              "Ignore default routes, regardless of route type";
            type boolean;
            default "true";
          }
        }
        container tunnel-resolution {
          description
            "Options related to resolution using tunnels in the tunnel table";
          uses allowed-tunnel-types-evpn-ipvpn-mpls;
          uses color-aware-next-hop-resolution {
            if-feature "srl_nokia-feat:bgp-next-hop-resolution-tag or srl_nokia-feat:isis-flex-algo or srl_nokia-feat:segment-routing-colored-te-policies";
          }
        }
      }
      container ipv6-next-hops {
        description
          "Options related to the resolution of BGP next-hops that are IPv6 addresses";
        container route-resolution {
          description
            "Options related to resolution using IP routes in the FIB";
          leaf admin-state {
            description
              "Enable or disable route resolution if no resolving tunnel is found";
            type srl_nokia-comm:admin-state;
            default "enable";
          }
          leaf ignore-default-routes {
            description
              "Ignore default routes, regardless of route type";
            type boolean;
            default "true";
          }
        }
        container tunnel-resolution {
          description
            "Options related to resolution using tunnels in the tunnel table";
          uses allowed-tunnel-types-evpn-ipvpn-mpls;
          uses color-aware-next-hop-resolution {
            if-feature "srl_nokia-feat:bgp-next-hop-resolution-tag or srl_nokia-feat:isis-flex-algo or srl_nokia-feat:segment-routing-colored-te-policies";
          }
        }
      }
    }
  }

  grouping selective-label-route-optimizations {
    container selective-labeled-unicast-install {
      if-feature "srl_nokia-feat:bgp-labeled-unicast-selective-install";
      presence "Do not install labeled-unicast routes as tunnels in the tunnel-table unless they match the next-hop of a locally installed VPN route";
      must "../../../../../srl_nokia-netinst:type = 'srl_nokia-netinst:default'" {
        error-message "selective-labeled-unicast-install is not supported in network instance other than default";
      }
      leaf program-label-swap {
        description
          "When true, program a label swap entry even when the route is not installed as a tunnel";
        type boolean;
        default "false";
        must '. = true() or ../program-route = false()' {
          error-message "If program-label-swap is false then program-route must be false";
        }
      }
      leaf program-route {
        description
          "When true, program IP FIB entry even when the route is not installed as a tunnel";
        type boolean;
        default "false";
      }
    }
  }

  grouping link-bandwidth {
    description
      "Grouping containing the configuration and state for unequal ECMP";
    container link-bandwidth {
      if-feature "srl_nokia-feat:evpn-ifl-unequal-ecmp or srl_nokia-feat:bgp-weighted-ecmp";
      leaf add-next-hop-count-to-received-bgp-routes {
        if-feature "srl_nokia-feat:evpn-ifl-unequal-ecmp";
        must "/srl_nokia-netinst:network-instance[srl_nokia-netinst:name = current()/../../../../../../../srl_nokia-netinst:name]/srl_nokia-netinst:type = 'srl_nokia-netinst:ip-vrf'" {
          error-message "Add next-hop count weight is only supported in network instances of type ip-vrf";
        }
        type union {
          type int32 {
            range "1..128";
          }
          type enumeration {
            enum disable {
              value -1;
            }
          }
        }
        description
          "Determines the weight that is internally added to the received PE-CE BGP routes

           The configured weight is added to all received BGP PE-CE routes for the purpose of EVPN unequal ECMP.
           This weight is internal and not added into any link-bandwidth extended community when readvertising
           the received routes to other ipv4 or ipv6 neighbors.";
      }
      leaf aggregate-used-paths {
        if-feature "srl_nokia-feat:bgp-weighted-ecmp";
        description
          "When advertising link-bandwidth to this peer, sum the link bandwidth from all the used multipaths";
        type boolean;
      }
    }
  }

  grouping bgp-label-instance {
    container bgp-label {
      presence "Enable BGP labeled route support";
      if-feature "srl_nokia-feat:bgp-labeled-unicast or srl_nokia-feat:inter-as-nhsrr-ipvpn or srl_nokia-feat:nhsrr-evpn";
      must '(/srl_nokia-netinst:network-instance[srl_nokia-netinst:name = current()/../../../srl_nokia-netinst:name]/srl_nokia-netinst:type = "srl_nokia-netinst:default")' {
        error-message "Labeled BGP configuration is only possible in network-instance of type default";
      }
      container labeled-unicast {
        if-feature "srl_nokia-feat:label-management and srl_nokia-feat:bgp-labeled-unicast";
        leaf dynamic-label-block {
          type leafref {
            path "/srl_nokia-system:system/srl_nokia-mplslbl:mpls/srl_nokia-mplslbl:label-ranges/srl_nokia-mplslbl:dynamic/srl_nokia-mplslbl:name";
          }
          description
            "Reference to a dynamic label block";
        }
        leaf dynamic-label-block-status {
          config false;
          type enumeration {
            enum available;
            enum unavailable;
          }
          description
            "Status of the label block.

             The label block may show as unavailable if there is pending cleanup.";
        }
        uses entropy-label;
        uses selective-label-route-optimizations;
      }
      container bgp-vpn {
        if-feature "srl_nokia-feat:label-management and (srl_nokia-feat:inter-as-nhsrr-ipvpn or srl_nokia-feat:nhsrr-evpn)";
        leaf dynamic-label-block {
          type leafref {
            path "/srl_nokia-system:system/srl_nokia-mplslbl:mpls/srl_nokia-mplslbl:label-ranges/srl_nokia-mplslbl:dynamic/srl_nokia-mplslbl:name";
          }
          description
            "Reference to a dynamic label block used for non-local BGP VPN routes advertised with next-hop-self";
        }
        leaf dynamic-label-block-status {
          config false;
          type enumeration {
            enum available;
            enum unavailable;
          }
          description
            "Status of the label block.

             The label block may show as unavailable if there is pending cleanup.";
        }
      }
      container bgp-ipvpn {
        if-feature "srl_nokia-feat:inter-as-nhsrr-ipvpn";
        uses next-hop-resolution-evpn-ipvpn-mpls;
      }
    }
  }

  grouping rib-management {
    container rib-management {
      if-feature "srl_nokia-feat:bgp-labeled-unicast";
      list table {
        must "/srl_nokia-netinst:network-instance[srl_nokia-netinst:name = current()/../../../../srl_nokia-netinst:name]/srl_nokia-netinst:type = 'srl_nokia-netinst:default'" {
          error-message "RIB management not supported in network-instances other than default";
        }
        key "address-family";
        leaf address-family {
          description
            "BGP address family";
          type identityref {
            base srl_nokia-comm:bgp-address-family;
          }
          must ". = 'ipv4-unicast' or . = 'ipv6-unicast' or . = 'ipv4-labeled-unicast' or . = 'ipv6-labeled-unicast'" {
            srl_nokia-ext:if-feature "srl_nokia-feat:bgp-labeled-unicast-future";
            error-message "unsupported address family";
          }
          must ". = 'ipv4-labeled-unicast' or . = 'ipv6-labeled-unicast'" {
            srl_nokia-ext:if-feature "not srl_nokia-feat:bgp-labeled-unicast-future";
            error-message "unsupported address family";
          }
        }
        description
          "List of RIB tables maintained by BGP running in this network-instance";
        leaf route-table-import {
          description
            "Apply a route policy to accept routes that should be installed in the BGP RIB table";
          type leafref {
            path "/srl-rpol:routing-policy/srl-rpol:policy/srl-rpol:name";
          }
        }
      }
    }
  }

  grouping segment-routing {
    container segment-routing-mpls {
      if-feature "srl_nokia-feat:bgp-labeled-unicast-prefix-sid";
      description
        "BGP support for segment routing using MPLS dataplane";
      leaf admin-state {
        description
          "Enable SR-MPLS support within BGP";
        type srl_nokia-comm:admin-state;
        default "disable";
        must ". = 'disable' or ../../../../srl_nokia-sr:segment-routing/srl_nokia-sr:mpls" {
          error-message "To enable, sr-mpls not enabled in the network-instance";
        }
      }
    }
  }

  grouping bgp-top {
    container bgp {
      presence "Configure BGP";
      must 'not(/srl_nokia-netinst:network-instance[srl_nokia-netinst:name = current()/../../srl_nokia-netinst:name]/srl_nokia-netinst:type = "srl_nokia-netinst:mac-vrf")' {
        error-message "BGP configuration is not possible on network-instance of type mac-vrf ";
      }
      must "../../srl_nokia-netinst:type != 'srl_nokia-netinst:host'" {
        error-message "BGP not supported with network-instance of type host";
      }
      leaf admin-state {
        type srl_nokia-comm:admin-state;
        default "enable";
        must " (. = 'disable') or
               (../afi-safi[afi-safi-name='ipv4-unicast']/admin-state = 'enable') or
               (../afi-safi[afi-safi-name='ipv6-unicast']/admin-state = 'enable') or
               (../afi-safi[afi-safi-name='evpn']/admin-state = 'enable') or
               (../afi-safi[afi-safi-name='ipv4-labeled-unicast']/admin-state = 'enable') or
               (../afi-safi[afi-safi-name='ipv6-labeled-unicast']/admin-state = 'enable') or
               (../afi-safi[afi-safi-name='l3vpn-ipv4-unicast']/admin-state = 'enable') or
               (../afi-safi[afi-safi-name='l3vpn-ipv6-unicast']/admin-state = 'enable') or
               (../afi-safi[afi-safi-name='route-target']/admin-state = 'enable') or
               (../afi-safi[afi-safi-name='sr-policy-ipv4']/admin-state = 'enable') or
               (../afi-safi[afi-safi-name='sr-policy-ipv6']/admin-state = 'enable')" {
          error-message "One of the address families must be enabled.";
        }
        description
          "Administratively enable or disable the entire BGP instance

           Disable causes all BGP sessions to be taken down immediately, even if admin-state at the group or neighbor level of some of these sessions is still set as enable.";
      }
      leaf oper-state {
        config false;
        type enumeration {
          enum up {
            description
              "Operational state of BGP is up.";
          }
          enum down {
            description
              "Operational state of BGP is down.";
          }
        }
      }
      leaf under-maintenance {
        config false;
        type boolean;
        description
          "State field to determine if the bgp instance is in maintenance mode.";
      }
      leaf maintenance-group {
        config false;
        type string;
        description
          "State field to display the maintenance group to which this bgp instance belongs to.";
      }
      leaf autonomous-system {
        type srl_nokia-comm:as-number;
        mandatory true;
        description
          "The global AS number of the BGP instance

           Values greater than 65535 must be entered in ASPLAIN format.";
      }
      uses bgp-policy;
      leaf local-preference {
        type uint32;
        default "100";
        description
          "The value of the local-preference attribute that is added to received routes from EBGP peers

           It is also used to encode the local preference attribute for locally generated BGP routes.";
      }
      leaf router-id {
        type srl_nokia-comm:ip-address;
        mandatory true;
        description
          "The BGP identifier used by this BGP instance in all of its OPEN messages

           Any non-zero value is supported.";
      }
      container as-path-options {
        description
          "Options for handling the AS_PATH in received BGP routes";
        leaf allow-own-as {
          type uint8;
          default "0";
          description
            "The maximum number of times the global AS number or a local AS number of the BGP instance can appear in any received AS_PATH before it is considered a loop and considered invalid";
        }
        container remove-private-as {
          description
            "Container with options for removing private AS numbers (2-byte and 4-byte) from the advertised AS path towards all peers";
          leaf mode {
            description
              "The method by which private AS numbers are removed from the advertised AS_PATH attribute";
            type enumeration {
              enum disabled {
                description
                  "Do not strip or replace any private AS numbers";
              }
              enum delete {
                description
                  "Delete private AS numbers, shortening the AS path";
              }
              enum replace {
                description
                  "Replace private AS numbers with the local AS number used towards the peer, maintaining the AS path length";
              }
            }
            default "disabled";
          }
          leaf leading-only {
            description
              "If set to true then only delete or replace private AS numbers that appear before the first occurrence of a non-private ASN in the sequence of most recent ASNs in the AS path";
            type boolean;
            must "not(../mode = 'disabled' and . = true())" {
              error-message "mode should not be disabled to set leading-only to true.";
            }
            default "false";
          }
          leaf ignore-peer-as {
            description
              "If set to true then do not delete or replace a private AS number that is the same as the peer AS number";
            type boolean;
            must "not(../mode = 'disabled' and . = true())" {
              error-message "mode should not be disabled if ignore-peer-as has to be true.";
            }
            default "false";
          }
        }
      }
      container authentication {
        description
          "Container with authentication options that apply to all peers of the BGP instance";
        leaf keychain {
          description
            "Reference to a keychain. The keychain type must be tcp-md5.";
          type leafref {
            path "/srl_nokia-system:system/srl-keychain:authentication/srl-keychain:keychain/srl-keychain:name";
          }
          must '/srl_nokia-system:system/srl-keychain:authentication/srl-keychain:keychain[srl-keychain:name = current()]'
             + '/srl-keychain:type = "tcp-md5"' {
            error-message "Only keychain of type tcp-md5 can be assigned";
          }
        }
        leaf password {
          if-feature "srl_nokia-feat:bgp-auth-password";
          description
            "Configures an MD5 authentication password for use with neighboring devices.";
          type srl_nokia-comm:routing-password;
          must 'boolean(../keychain) = false()' {
            error-message "Can not assign both keychain and password";
          }
        }
      }
      container best-path-selection {
        if-feature "srl_nokia-feat:routing-policy-bgp-med";
        description
          "Container with options that control the BGP decision process (tie break between routes for the same NLRI).";
        leaf always-compare-med {
          type boolean;
          default "false";
          description
            "Compare multi-exit discriminator (MED) value from different ASes when selecting the best route. The default behavior is to only compare MEDs for paths received from the same AS.";
        }
        leaf advertise-inactive {
          if-feature "srl_nokia-feat:bgp-labeled-unicast";
          description
            "Advertise the best BGP route even if it is inactive due to the programming of a better non-BGP route";
          type boolean;
          default "false";
        }
      }
      uses bgp-label-instance;
      container convergence {
        description
          "Options for configuring address family independent BGP convergence parameters";
        leaf min-wait-to-advertise {
          type uint16 {
            range "0..3600";
          }
          default "0";
          description
            "The minimum amount of time, in seconds, measured from the moment when the first session (configured or dynamic) comes up after a BGP restart, until BGP is allowed to advertise any routes to any peer

             The sessions that are established when this timer expires determines the set of peers from which EOR is expected in order to declare convergence for an address family. A value of 0 means the feature is disabled and all routes are advertised immediately.

             This timer and associated state machine are only restarted by one of the following triggers:
             - BGP instance admin disable/enable
             - tools clear network-instance protocols bgp reset-peer
             - bgp application restart
             - node reboot";
        }
      }
      container dynamic-neighbors {
        description
          "Options related to the acceptance and initiation of dynamic BGP sessions";
        container accept {
          description
            "Options related to the acceptance of dynamic BGP sessions from remote peers";
          list match {
            description
              "List of prefix and group-id combinations from which incoming TCP connections to port 179 will be accepted

               An incoming TCP connection to port 179 is matched to a list entry if:
               (a) the source IP does not match a configured BGP neighbor address
               (b) the list entry prefix is the longest prefix match of the source IP.
               (c) the source IP is not an IPv6 link-local address associated with an (unnumbered) interface configured for dynamic-neighbor sessions.";
            key "prefix";
            leaf prefix {
              type srl_nokia-comm:ip-prefix;
              description
                "The IP prefix used to match an incoming dynamic BGP session to a group.";
            }
            leaf-list allowed-peer-as {
              type string {
                pattern '([1-9][0-9]*)|([1-9][0-9]*)\.\.([1-9][0-9]*)';
              }
              ordered-by user;
              max-elements 32;
              description
                "The allowed AS numbers that can establish incoming BGP sessions from this prefix and group-id-range combination

                 If the OPEN message from a peer matched to this prefix contains a MyAS number that is not in this allowed list then a NOTIFICATION is sent to the peer with the indication Bad Peer AS. Each entry in this list can be a single AS number or a range of AS numbers in the format as1..as2";
            }
            leaf peer-group {
              type leafref {
                path "../../../../group/group-name";
              }
              description
                "Reference to a peer-group

                 When an incoming session is matched to this list entry it is associated with the peer-group referenced by this leaf. The peer-group provides all the parameters needed to complete the establishment of the dynamic session. If the referenced peer-group has a configured peer-as this is ignored by dynamic BGP sessions using the group as a template.";
              mandatory true;
            }
          }
          leaf max-sessions {
            type uint16;
            default "0";
            description
              "The maximum number of incoming BGP sessions that will be accepted by the router

               A value of 0 means no limit.";
          }
        }
        list interface {
          if-feature "srl_nokia-feat:bgp-unnumbered-peers";
          description
            "List of interfaces on which dynamic sessions based on IPv6 link-local address discovery are accepted and initiated.";
          key "interface-name";
          leaf interface-name {
            description
              "Reference to a specific subinterface of the form <interface-name>.<subinterface-index>

               The referenced subinterface should be enabled for IPv6 and should be configured to accept and send IPv6 router advertisement messages. The referenced subinterface does not need any IPv4 addresses or global-unicast IPv6 addresses (i.e. it can be an unnumbered interface).

               When a subinterface is present in this list, incoming TCP connections to the BGP well-known port that are received on this subinterface and sourced from an IPv6 link local address and destined for the IPv6 link local address of the subinterface are automatically accepted.

               When a subinterface is present in this list, received IPv6 router advertisement messages on this subinterface automatically trigger BGP session setup towards the sender of these messages, if there is not already an established session.";
            type srl_nokia-comm:subinterface-all;
          }
          leaf-list allowed-peer-as {
            type string {
              pattern '([1-9][0-9]*)|([1-9][0-9]*)\.\.([1-9][0-9]*)';
            }
            ordered-by user;
            max-elements 32;
            description
              "Specifies the allowed AS numbers of dynamic BGP neighbors on this interface. If the OPEN message from a peer on this interface contains a MyAS number that is not in this allowed list then a NOTIFICATION is sent to the peer with the indication Bad Peer AS. Each entry in this list can be a single AS number or a range of AS numbers in the string format as1..as2.";
          }
          leaf peer-group {
            type leafref {
              path "../../../srl_nokia-bgp:group/srl_nokia-bgp:group-name";
            }
            description
              "Reference to a peer-group
               Specifies the peer-group to associate with dynamic BGP neighbors on this interface. The peer-group provides all the parameters needed to complete the establishment of the dynamic session.";
            mandatory true;
          }
          leaf max-sessions {
            type uint16;
            default "1";
            description
              "The maximum number of dynamic sessions that are allowed to be setup on the interface as a result of accepting sessions from link-local addresses or initiating
               sessions by means of receiving IPv6 router advertisements.";
          }
        }
      }
      container ebgp-default-policy {
        description
          "Options for controlling the default policies that apply to EBGP sessions";
        leaf import-reject-all {
          type boolean;
          default "true";
          description
            "When set to true, all inbound routes from any EBGP peer to which no explicit import policy is applied are treated as though they were rejected by policy";
        }
        leaf export-reject-all {
          type boolean;
          default "true";
          description
            "When set to true, all outbound routes towards any EBGP peer to which no explicit export policy is applied are treated as though they were rejected by policy";
        }
      }
      container failure-detection {
        description
          "Options related to methods of detecting BGP session failure";
        leaf enable-bfd {
          if-feature "srl_nokia-feat:bfd";
          type boolean;
          default "false";
          description
            "The true setting enables Bi-directional Forwarding Detection on BGP sessions belonging to the peer group";
        }
        leaf fast-failover {
          type boolean;
          default "true";
          description
            "The true setting causes EBGP and IBGP sessions to drop immediately (and not wait for hold timer expiry) when the local interface that they depend upon for neighbor reachability goes down";
        }
      }
      container graceful-restart {
        description
          "Options for controlling the behavior of the router as a graceful restart helper";
        leaf admin-state {
          type srl_nokia-comm:admin-state;
          default "disable";
          description
            "Administratively enable or disable graceful restart helper for all address families";
        }
        leaf stale-routes-time {
          type uint16 {
            range "1..3600";
          }
          units "seconds";
          default "360";
          description
            "The maximum number of seconds that routes received from a helped peer remain stale until they are deleted

             Routes of AFI/SAFI X received from peer Y are marked stale when peer Y goes down and its previous GR capability included AFI/SAFI X.";
        }
        leaf requested-restart-time {
          if-feature "srl_nokia-feat:bgp-graceful-restart-gaps";
          description
            "The restart time encoded in this router's GR capability.

             If the neighbor honors this request then this is the maximum time allowed for this router to re-establish its TCP connection after a restart. If this time is exceeded, the neighbor is expected to flush stale routes that it was maintaining on behalf of this router.";
          type uint16 {
            range "1..3600";
          }
          units "seconds";
          default "300";
        }
      }
      leaf max-ecmp-hash-buckets-per-next-hop-group {
        if-feature "srl_nokia-feat:bgp-max-ecmp-hash-buckets";
        type uint16 {
          range "1..256";
        }
        description
          "Specifies the maximum number of ECMP hash buckets per next-hop-group

           Weighted ECMP weights are normalized based on this number of hash buckets.";
        must '. <= 64' {
          error-message "Valid range for max-ecmp-hash-buckets-per-next-hop-group:[1..64] ";
          srl_nokia-ext:if-feature "srl_nokia-feat:fpcx";
        }
        must '. <= 128' {
          error-message "Valid range for max-ecmp-hash-buckets-per-next-hop-group:[1..128] ";
          srl_nokia-ext:if-feature "srl_nokia-feat:trident3 or srl_nokia-feat:trident4";
        }
        must '. <= 256' {
          error-message "Valid range for max-ecmp-hash-buckets-per-next-hop-group:[1..256] ";
          srl_nokia-ext:if-feature "srl_nokia-feat:jericho2 or srl_nokia-feat:jericho2cp";
        }
        must '(. <= 8)' {
          srl_nokia-ext:if-feature "srl_nokia-features:platform-7215-a1";
          error-message "Value cannot be greater than 8 on the 7215 IXS-A1 platform.";
        }
      }
      list afi-safi {
        key "afi-safi-name";
        description
          "List of address families supported by the BGP instance";
        leaf afi-safi-name {
          type identityref {
            base srl_nokia-comm:bgp-address-family;
          }
          description
            "The name of a BGP address family, which translates to a specific AFI value and a specific SAFI value";
          must "not(. = 'evpn') or /srl_nokia-netinst:network-instance[srl_nokia-netinst:name = current()/../../../../srl_nokia-netinst:name]/srl_nokia-netinst:type = 'srl_nokia-netinst:default'" {
            error-message "EVPN is not supported in network instances other than default";
          }
          must "not(. = 'route-target') or /srl_nokia-netinst:network-instance[srl_nokia-netinst:name = current()/../../../../srl_nokia-netinst:name]/srl_nokia-netinst:type = 'srl_nokia-netinst:default'" {
            error-message "route-target is not supported in network instances other than default";
          }
          must "not(. = 'l3vpn-ipv4-unicast')  or /srl_nokia-netinst:network-instance[srl_nokia-netinst:name = current()/../../../../srl_nokia-netinst:name]/srl_nokia-netinst:type = 'srl_nokia-netinst:default'" {
            error-message "L3VPN is not supported in network instances other than default";
          }
          must "not(. = 'l3vpn-ipv6-unicast') or /srl_nokia-netinst:network-instance[srl_nokia-netinst:name = current()/../../../../srl_nokia-netinst:name]/srl_nokia-netinst:type = 'srl_nokia-netinst:default'" {
            error-message "L3VPN is not supported in network instances other than default";
          }
          must "not(. = 'ipv4-labeled-unicast') or /srl_nokia-netinst:network-instance[srl_nokia-netinst:name = current()/../../../../srl_nokia-netinst:name]/srl_nokia-netinst:type = 'srl_nokia-netinst:default'" {
            error-message "Label-IPv4 is not supported in network instances other than default";
          }
          must "not(. = 'ipv6-labeled-unicast') or /srl_nokia-netinst:network-instance[srl_nokia-netinst:name = current()/../../../../srl_nokia-netinst:name]/srl_nokia-netinst:type = 'srl_nokia-netinst:default'" {
            error-message "Label-IPv6 is not supported in network instances other than default";
          }
          must "not(. = 'sr-policy-ipv4') or /srl_nokia-netinst:network-instance[srl_nokia-netinst:name = current()/../../../../srl_nokia-netinst:name]/srl_nokia-netinst:type = 'srl_nokia-netinst:default'" {
            error-message "sr-policy-ipv4 is not supported in network instances other than default";
          }
          must "not(. = 'sr-policy-ipv6') or /srl_nokia-netinst:network-instance[srl_nokia-netinst:name = current()/../../../../srl_nokia-netinst:name]/srl_nokia-netinst:type = 'srl_nokia-netinst:default'" {
            error-message "sr-policy-ipv6 is not supported in network instances other than default";
          }
        }
        leaf admin-state {
          type srl_nokia-comm:admin-state;
          default "disable";
          description
            "This leaf indicates whether the AFI-SAFI is enabled for the instance";
        }
        uses bgp-afi-safi-policy;
        container add-paths {
          if-feature "srl_nokia-feat:bgp-add-paths";
          description
            "Configure support for the advertisement and receipt of multiple paths for the AFI/SAFI";
          leaf receive {
            type boolean;
            description
              "Enable capability negotiation to receive multiple path advertisements from a single peer for a single NLRI belonging to the AFI/SAFI";
            must "../../afi-safi-name != 'ipv4-labeled-unicast'" {
              srl_nokia-ext:if-feature "not srl_nokia-feat:bgp-add-paths-labeled-unicast";
              error-message "add-paths is not supported for address familiy ipv4-labeled-unicast";
            }
            must "../../afi-safi-name != 'ipv6-labeled-unicast'" {
              srl_nokia-ext:if-feature "not srl_nokia-feat:bgp-add-paths-labeled-unicast";
              error-message "add-paths is not supported for address familiy ipv6-labeled-unicast";
            }
            must "../../afi-safi-name != 'l3vpn-ipv4-unicast'" {
              srl_nokia-ext:if-feature "not srl_nokia-feat:bgp-add-paths-l3vpn";
              error-message "add-paths is not supported for address familiy l3vpn-ipv4-unicast";
            }
            must "../../afi-safi-name != 'l3vpn-ipv6-unicast'" {
              srl_nokia-ext:if-feature "not srl_nokia-feat:bgp-add-paths-l3vpn";
              error-message "add-paths is not supported for address familiy l3vpn-ipv6-unicast";
            }
            must "../../afi-safi-name != 'evpn'" {
              srl_nokia-ext:if-feature "not srl_nokia-feat:bgp-add-paths-evpn";
              error-message "add-paths is not supported for address familiy evpn";
            }
            must "../../afi-safi-name != 'route-target'" {
              error-message "add-paths is not supported for address family route-target";
            }
            must "../../afi-safi-name != 'sr-policy-ipv4'" {
              error-message "add-paths is not supported for address family sr-policy-ipv4";
            }
            must "../../afi-safi-name != 'sr-policy-ipv6'" {
              error-message "add-paths is not supported for address family sr-policy-ipv6";
            }
          }
          leaf send {
            type boolean;
            description
              "Enable capability negotiation to send multiple path advertisements to a single peer for a single NLRI belonging to the AFI/SAFI";
            must "../../afi-safi-name != 'ipv4-labeled-unicast'" {
              srl_nokia-ext:if-feature "not srl_nokia-feat:bgp-add-paths-labeled-unicast";
              error-message "add-paths is not supported for address familiy ipv4-labeled-unicast";
            }
            must "../../afi-safi-name != 'ipv6-labeled-unicast'" {
              srl_nokia-ext:if-feature "not srl_nokia-feat:bgp-add-paths-labeled-unicast";
              error-message "add-paths is not supported for address familiy ipv6-labeled-unicast";
            }
            must "../../afi-safi-name != 'l3vpn-ipv4-unicast'" {
              srl_nokia-ext:if-feature "not srl_nokia-feat:bgp-add-paths-l3vpn";
              error-message "add-paths is not supported for address familiy l3vpn-ipv4-unicast";
            }
            must "../../afi-safi-name != 'l3vpn-ipv6-unicast'" {
              srl_nokia-ext:if-feature "not srl_nokia-feat:bgp-add-paths-l3vpn";
              error-message "add-paths is not supported for address familiy l3vpn-ipv6-unicast";
            }
            must "../../afi-safi-name != 'evpn'" {
              srl_nokia-ext:if-feature "not srl_nokia-feat:bgp-add-paths-evpn";
              error-message "add-paths is not supported for address familiy evpn";
            }
            must "../../afi-safi-name != 'route-target'" {
              error-message "add-paths is not supported for address family route-target";
            }
            must "../../afi-safi-name != 'sr-policy-ipv4'" {
              error-message "add-paths is not supported for address family sr-policy-ipv4";
            }
            must "../../afi-safi-name != 'sr-policy-ipv6'" {
              error-message "add-paths is not supported for address family sr-policy-ipv6";
            }
          }
          choice selection-algorithm {
            leaf send-max {
              type uint8 {
                range "1..16";
              }
              description
                "Send the N best paths for a single NLRI, or as many as possible until there are no more valid paths to send.

                 This ensures the best path is advertised but does not limit the additional paths to being 'used' paths.";
              must '../send = true()' {
                error-message "send capability must be advertised";
              }
            }
            leaf send-multipath {
              type empty;
              description
                "Send the used paths for a single NLRI, including all paths that are multipaths.";
              must '../send = true()' {
                error-message "send capability must be advertised";
              }
            }
          }
          leaf eligible-prefix-policy {
            if-feature "srl_nokia-feat:bgp-add-paths-policy-control";
            description
              "Specifies a route policy to control the set prefixes that are eligible for the add-paths send behavior

               If no policy is configured: advertise add-paths for every prefix according to the afi-safi configuration
               If a policy is configured and there is no match: advertise add-paths for the prefix according to the afi-safi configuration
               If a policy is configured and a route for prefix P is matched with an accept action: advertise add-paths for the prefix P according to the afi-safi configuration
               If a policy is configured and a route for prefix P is matched with a reject action: no add-paths are advertised for prefix P";
            type leafref {
              path "/srl-rpol:routing-policy/srl-rpol:policy/srl-rpol:name";
            }
          }
        }
        uses multipath-family-config;
        uses weighted-ecmp-family-config;
        leaf received-routes {
          config false;
          type srl_nokia-comm:zero-based-counter64;
          description
            "The total number of routes belonging to this AFI/SAFI received from all peers of the BGP instance";
        }
        leaf active-routes {
          config false;
          type srl_nokia-comm:zero-based-counter64;
          description
            "The total number of routes belonging to this AFI/SAFI that are installed and used, being best routes";
        }
        container ipv4-unicast {
          description
            "Options related to the IPv4-unicast address family";
          uses rfc-8950-instance;
          uses backup-paths-family-config {
            if-feature "srl_nokia-feat:bgp-backup-path-frr-ip";
          }
          uses convergence-for-family;
          uses next-hop-resolution-unlabeled;
        }
        container ipv4-labeled-unicast {
          if-feature "srl_nokia-feat:bgp-labeled-unicast";
          description
            "Options related to the labeled IPv4-unicast address family";
          uses rfc-8950-instance {
            if-feature "srl_nokia-feat:bgp-labeled-unicast-future";
          }
          uses backup-paths-family-config {
            if-feature "srl_nokia-feat:bgp-backup-path-frr-label-ip";
          }
          uses convergence-for-family;
          uses next-hop-resolution-labeled;
          leaf rapid-update {
            description
              "When true, label-ipv4 update messages are advertised immediately, bypassing the MRAI

               When this is false, reachability updates and withdrawals are subject to the MRAI interval.";
            type boolean;
            default "false";
          }
        }
        container l3vpn-ipv4-unicast {
          if-feature "srl_nokia-feat:inter-as-nhsrr-ipvpn or srl_nokia-feat:ipvpn";
          description
            "Options related to the VPN-IPv4 unicast address family";
          uses rfc-8950-instance;
          uses convergence-for-family;
          leaf keep-all-routes {
            description
              "When this is set to true all received VPN-IPv4 routes are retained in the RIB-IN, even those not imported by any network-instance; these routes display as 'rejected' and cannot be propagated to other peers

               When this is false, VPN-IPv4 routes that are not imported by any network-instance are dropped and not retained in the BGP RIB-IN; policy changes affecting received VPN-IPv4 routes will trigger the sending of ROUTE_REFRESH messages towards all VPN-IPv4 family peers.";
            type boolean;
            default "false";
            must ". = false() or (/srl_nokia-netinst:network-instance[srl_nokia-netinst:name = current()/../../../../../srl_nokia-netinst:name]/srl_nokia-netinst:type = 'srl_nokia-netinst:default')" {
              error-message "VPN-IPv4 is not supported in network instances other than default";
            }
          }
          leaf next-hop-self-route-reflector {
            if-feature "srl_nokia-feat:inter-as-nhsrr-ipvpn";
            description
              "When set to true, received VPN-IPv4 routes are kept in the RIB and readvertised to the other route reflector clients with a local next-hop and VPN label

               This command triggers the programming of a VPN label swap operation for each received VPN-IPv4 route.";
            type boolean;
            default "false";
            must ". = false() or (/srl_nokia-netinst:network-instance[srl_nokia-netinst:name = current()/../../../../../srl_nokia-netinst:name]/srl_nokia-netinst:type = 'srl_nokia-netinst:default')" {
              error-message "VPN-IPv4 is not supported in network instances other than default";
            }
          }
          leaf inter-as-vpn {
            if-feature "srl_nokia-feat:inter-as-nhsrr-ipvpn";
            description
              "When set to true, received VPN-IPv4 routes that are not imported by any network-instance are retained in the BGP RIB and considered 'used' so that they can be propagated to any EBGP or IBGP peer.

               This command supersedes the effect of keep-all-routes. This command triggers the programming of a VPN label swap operation for each received VPN-IPv4 route.";
            type boolean;
            default "false";
            must ". = false() or (/srl_nokia-netinst:network-instance[srl_nokia-netinst:name = current()/../../../../../srl_nokia-netinst:name]/srl_nokia-netinst:type = 'srl_nokia-netinst:default')" {
              error-message "VPN-IPv4 is not supported in network instances other than default";
            }
          }
          leaf rapid-update {
            description
              "When true, vpn-ipv4 update messages are advertised immediately, bypassing the MRAI

               When this is false, reachability updates and withdrawals are subject to the MRAI interval.";
            type boolean;
            default "false";
          }
        }
        container ipv6-unicast {
          description
            "Options related to the IPv6-unicast address family";
          uses backup-paths-family-config {
            if-feature "srl_nokia-feat:bgp-backup-path-frr-ip";
          }
          uses convergence-for-family;
          uses next-hop-resolution-unlabeled;
        }
        container ipv6-labeled-unicast {
          if-feature "srl_nokia-feat:bgp-labeled-unicast";
          description
            "Options related to the labeled IPv6-unicast address family";
          uses backup-paths-family-config {
            if-feature "srl_nokia-feat:bgp-backup-path-frr-label-ip";
          }
          uses convergence-for-family;
          uses next-hop-resolution-labeled;
          leaf rapid-update {
            description
              "When true, label-ipv6 update messages are advertised immediately, bypassing the MRAI

               When this is false, reachability updates and withdrawals are subject to the MRAI interval.";
            type boolean;
            default "false";
          }
        }
        container l3vpn-ipv6-unicast {
          if-feature "srl_nokia-feat:inter-as-nhsrr-ipvpn or srl_nokia-feat:ipvpn";
          description
            "Options related to the VPN-IPv6 unicast address family";
          uses convergence-for-family;
          leaf keep-all-routes {
            description
              "When this is set to true all received VPN-IPv6 routes are retained in the RIB-IN, even those not imported by any network-instance; these routes display as 'rejected' and cannot be propagated to other peers

               When this is false, VPN-IPv6 routes that are not imported by any network-instance are dropped and not retained in the BGP RIB-IN; policy changes affecting received VPN-IPv6 routes will trigger the sending of ROUTE_REFRESH messages towards all VPN-IPv6 family peers.";
            type boolean;
            default "false";
            must ". = false() or (/srl_nokia-netinst:network-instance[srl_nokia-netinst:name = current()/../../../../../srl_nokia-netinst:name]/srl_nokia-netinst:type = 'srl_nokia-netinst:default')" {
              error-message "VPN-IPv6 is not supported in network instances other than default";
            }
          }
          leaf next-hop-self-route-reflector {
            if-feature "srl_nokia-feat:inter-as-nhsrr-ipvpn";
            description
              "When set to true, received VPN-IPv6 routes are kept in the RIB and readvertised to the other route reflector clients with a local next-hop and VPN label

               This command triggers the programming of a VPN label swap operation for each received VPN-IPv6 route.";
            type boolean;
            default "false";
            must ". = false() or (/srl_nokia-netinst:network-instance[srl_nokia-netinst:name = current()/../../../../../srl_nokia-netinst:name]/srl_nokia-netinst:type = 'srl_nokia-netinst:default')" {
              error-message "VPN-IPv6 is not supported in network instances other than default";
            }
          }
          leaf inter-as-vpn {
            if-feature "srl_nokia-feat:inter-as-nhsrr-ipvpn";
            description
              "When set to true, received VPN-IPv6 routes that are not imported by any network-instance are retained in the BGP RIB and considered 'used' so that they can be propagated to any EBGP or IBGP peer.

               This command supersedes the effect of keep-all-routes. This command triggers the programming of a VPN label swap operation for each received VPN-IPv6 route.";
            type boolean;
            default "false";
            must ". = false() or (/srl_nokia-netinst:network-instance[srl_nokia-netinst:name = current()/../../../../../srl_nokia-netinst:name]/srl_nokia-netinst:type = 'srl_nokia-netinst:default')" {
              error-message "VPN-IPv6 is not supported in network instances other than default";
            }
          }
          leaf rapid-update {
            description
              "When true, vpn-ipv6 update messages are advertised immediately, bypassing the MRAI

               When this is false, reachability updates and withdrawals are subject to the MRAI interval.";
            type boolean;
            default "false";
          }
        }
        container evpn {
          description
            "Options related to the EVPN address family";
          leaf advertise-ipv6-next-hops {
            type boolean;
            default "false";
            must ". = false() or (/srl_nokia-netinst:network-instance[srl_nokia-netinst:name = current()/../../../../../srl_nokia-netinst:name]/srl_nokia-netinst:type = 'srl_nokia-netinst:default')" {
              error-message "EVPN is not supported in network instances other than default";
            }
            description
              "Enables advertisement of EVPN routes with IPv6 next-hops to peers

               If this is set to true and the local-address used towards the peer is an IPv6 address and BGP is supposed to apply next-hop-self then the route is advertised with the IPv6 local-address as the BGP next-hop. If this is set to false, then the EVPN route is advertised with an IPv4 next-hop.";
          }
          leaf keep-all-routes {
            description
              "When this is set to true all received EVPN routes are retained in the RIB-IN, even those not imported by any network-instance; these routes display as 'rejected' and cannot be propagated to other peers.

               When this is false, EVPN routes that are not imported by any network-instance are dropped and not retained in the BGP RIB-IN; policy changes affecting received EVPN routes will trigger the sending of ROUTE_REFRESH messages towards all EVPN family peers.";
            type boolean;
            default "false";
            must ". = false() or (/srl_nokia-netinst:network-instance[srl_nokia-netinst:name = current()/../../../../../srl_nokia-netinst:name]/srl_nokia-netinst:type = 'srl_nokia-netinst:default')" {
              error-message "EVPN is not supported in network instances other than default";
            }
          }
          uses next-hop-resolution-evpn-ipvpn-mpls {
            if-feature "srl_nokia-feat:nhsrr-evpn";
          }
          leaf next-hop-self-route-reflector {
            if-feature "srl_nokia-feat:nhsrr-evpn";
            description
              "When set to true, received EVPN MPLS routes are kept in the RIB and readvertised to the other route reflector clients with a local next-hop and EVI label

               This command triggers the programming of an EVI label swap operation for each received EVPN MPLS route.";
            type boolean;
            default "false";
            must ". = false() or (/srl_nokia-netinst:network-instance[srl_nokia-netinst:name = current()/../../../../../srl_nokia-netinst:name]/srl_nokia-netinst:type = 'srl_nokia-netinst:default')" {
              error-message "EVPN is not supported in network instances other than default";
            }
          }
          leaf inter-as-vpn {
            description
              "When set to true, received EVPN routes that are not imported by any network-instance are retained in the BGP RIB and considered 'used' so that they can be propagated to any EBGP or IBGP peer.

               This command supersedes the effect of keep-all-routes.";
            type boolean;
            default "false";
            must ". = false() or (/srl_nokia-netinst:network-instance[srl_nokia-netinst:name = current()/../../../../../srl_nokia-netinst:name]/srl_nokia-netinst:type = 'srl_nokia-netinst:default')" {
              error-message "EVPN is not supported in network instances other than default";
            }
          }
          leaf rapid-update {
            description
              "When this is set to true, EVPN UPDATEs advertising reachability and withdrawals are advertised immediately, bypassing the session level min-route-advertisement-interval. When this is false, reachability updates and withdrawals are subject to the MRAI interval.";
            type boolean;
            default "false";
            must ". = false() or (/srl_nokia-netinst:network-instance[srl_nokia-netinst:name = current()/../../../../../srl_nokia-netinst:name]/srl_nokia-netinst:type = 'srl_nokia-netinst:default')" {
              error-message "EVPN is not supported in network instances other than default";
            }
          }
          leaf default-received-encapsulation {
            if-feature "srl_nokia-feat:nhsrr-evpn";
            type enumeration {
              enum vxlan {
                value 1;
              }
              enum mpls {
                value 2;
              }
            }
            default "vxlan";
            description
              "Indicates the encapsulation considered when the routes are received without BGP encapsulation extended community

               Most EVPN routes are usually received with a BGP encapsulation extended community that indicates the encapsulation
               and therefore how to interpret the value in the received Label fields of the routes. If no encapsulation is
               received, BGP will validate the route as MPLS or VXLAN or SRv6 depending on how this command is configured.";
          }
        }
      }
      container preference {
        description
          "Options for controlling the route table preference of BGP routes";
        leaf ebgp {
          type uint8 {
            range "1..255";
          }
          default "170";
          description
            "The default route table preference for all EBGP learned routes

             BGP import policies can override this preference value on a route by route basis.";
        }
        leaf ibgp {
          type uint8 {
            range "1..255";
          }
          default "170";
          description
            "The default route table preference for all IBGP learned routes

             BGP import policies can override this preference value on a route by route basis.";
        }
      }
      uses rib-management;
      container route-advertisement {
        description
          "Options for controlling route advertisement behavior";
        leaf rapid-withdrawal {
          type boolean;
          default "false";
          description
            "The true setting enables rapid-withdraw towards BGP peers

             If there is only one BGP route for an NLRI in BGP RIB, and this route is withdrawn or becomes invalid, rapid-withdraw causes BGP to immediately send a withdrawal of the BGP route even if the min-route-advertisement timer has not expired.";
        }
        leaf wait-for-fib-install {
          type boolean;
          default "true";
          description
            "The true setting causes BGP to NOT advertise initial reachability to a prefix, or a change of reachability to a prefix, until it receives acknowledgment from FIB manager that the route change has been applied

             Does not apply to route withdrawals.";
        }
      }
      container route-flap-damping {
        if-feature "srl_nokia-feat:bgp-route-flap-damping";
        description
          "Configuration to control BGP route flap damping procedures";
        leaf half-life {
          description
            "Duration of time for the penalty amount (FOM) to be reduced by half if a route stays stable";
          type uint16 {
            range "1..45";
          }
          default "15";
          units "minutes";
        }
        leaf max-suppress-time {
          description
            "Maximum duration of time that advertisement of a route that has flapped can be suppressed";
          type uint16 {
            range "1..720";
          }
          default "60";
          units "minutes";
        }
        leaf reuse-threshold {
          description
            "A suppressed route can be advertised again after falling below this penalty (FOM) level";
          type uint16 {
            range "1..20000";
          }
          default "750";
        }
        leaf suppress-threshold {
          description
            "A flapping route is suppressed after rising above this penalty (FOM) level";
          type uint16 {
            range "1..20000";
          }
          default "3000";
        }
      }
      container route-reflector {
        description
          "Container with route reflection configuration options.";
        leaf client {
          description
            "When this is set to true all configured and dynamic sessions of the BGP instance are considered RR clients, subject to overrides at more specific levels of configuration.";
          type boolean;
          default "false";
        }
        leaf cluster-id {
          description
            "The cluster-id to insert into the CLUSTER_LIST attribute when reflecting routes received by or sent to clients in this scope of this container. The default is the router-id.";
          type cluster-id-type;
        }
      }
      uses segment-routing;
      container send-community {
        description
          "Options for controlling the sending of BGP communities to all peers";
        leaf standard {
          type boolean;
          default "true";
          description
            "The false setting causes BGP to strip all standard (4 byte) communities from all outbound routes advertised to peers";
        }
        leaf large {
          type boolean;
          default "true";
          description
            "The false setting causes BGP to strip all large (12 byte) BGP communities from all outbound routes advertised to peers";
        }
      }
      container transport {
        description
          "Options related to the TCP transport of BGP sessions";
        leaf single-hop-connected-check {
          if-feature "srl_nokia-feat:bgp-single-hop-connected-check";
          type boolean;
          default "true";
          description
            "Control whether a single-hop BGP session should be allowed to setup if its 'related interface' is down.

             If single-hop-connected-check is false, a single-hop BGP session (EBGP or IBGP) to any IPv4 or IPv6 neighbor address is permitted to establish if there is ANY valid (IPv6 global unicast, IPv4 link-local, or IPv4 global) route to that neighbor address, regardless of whether the 'related interface' is up or down.

             If single-hop-connected-check is true (default value), a single-hop BGP session (EBGP or IBGP) to any IPv4 or IPv6 neighbor address is only permitted to transition from idle to a higher state if the 'related interface' is up.

             The 'related interface' of a single hop peer is the subinterface associated with the IPv6 link local neighbor address or else the subinterface with a primary or secondary IP address and prefix-length that covers the neighbor address.";
        }
        leaf mtu-discovery {
          if-feature "srl_nokia-feat:bgp-mtu-discovery";
          type boolean;
          description
            "Turns path mtu discovery for BGP TCP sessions on (true) or off (false)

             If this is unconfigured then the setting comes from network-instance/mtu/path-mtu-discovery.

             Changing the value of network-instance/mtu/path-mtu-discovery takes effect only for new connections established after the change";
        }
        leaf tcp-mss {
          type uint16 {
            range "536..9446";
          }
          default "1024";
          description
            "The maximum segment size of BGP TCP packets

             The actual value used in the transmit direction towards a particular peer should be checked at the neighbor level.";
        }
      }
      uses traceoptions;
      container statistics {
        description
          "Container for BGP statistics.";
        config false;
        leaf total-paths {
          type srl_nokia-comm:zero-based-counter64;
          description
            "The total number of path attribute objects used by all received BGP routes";
        }
        leaf total-prefixes {
          config false;
          type uint64;
          description
            "The total number of unique NLRI contained in all received BGP routes associated with the BGP instance or the peer-group.";
        }
        leaf path-memory {
          type srl_nokia-comm:zero-based-counter64;
          description
            "The total number of bytes required to store the path attribute objects used by all received BGP routes";
        }
        leaf total-received-routes {
          type srl_nokia-comm:zero-based-counter64;
          description
            "The total number of received BGP routes, summed across all address families";
        }
        leaf total-active-routes {
          type srl_nokia-comm:zero-based-counter64;
          description
            "The total number of received BGP routes that are active (installed for forwarding), summed across all address families";
        }
        leaf total-decayed-routes {
          if-feature "srl_nokia-feat:bgp-route-flap-damping";
          type srl_nokia-comm:zero-based-counter64;
          description
            "The total number of received BGP routes that are eligible for use but have a route-flap-damping FOM greater than 0 and less than the suppress-threshold";
        }
        leaf total-history-routes {
          if-feature "srl_nokia-feat:bgp-route-flap-damping";
          type srl_nokia-comm:zero-based-counter64;
          description
            "The total number of recently withdrawn BGP routes that are still held in the BGP RIB because their route-flap-damping FOM is greater than 0";
        }
        leaf total-suppressed-routes {
          if-feature "srl_nokia-feat:bgp-route-flap-damping";
          type srl_nokia-comm:zero-based-counter64;
          description
            "The total number of received BGP routes that are suppressed because their route-flap-damping FOM is greater than the suppress-threshold";
        }
        leaf total-peers {
          type uint16;
          description
            "The total number of configured BGP peers";
        }
        leaf up-peers {
          type uint16;
          description
            "The number of configured BGP peers that are currently in the established state";
        }
        leaf disabled-peers {
          type uint16;
          description
            "The number of configured BGP peers that are administratively disabled";
        }
        leaf dynamic-peers {
          type uint16;
          description
            "The number of dynamic BGP peers that are currently in the established state, counting sessions resulting from accepted incoming TCP connections and outgoing TCP connections triggered by LLDP auto-discovery";
        }
      }
      uses bgp-group;
      uses bgp-neighbor;
    }
  }

  augment "/srl_nokia-netinst:network-instance/srl_nokia-netinst:protocols" {
    uses bgp-top;
  }

  augment "/srl_nokia-system:system/srl_nokia-system-protocols:protocols" {
    container bgp {
      presence "Configure system-wide BGP parameters";
      leaf restart-max-wait {
        description
          "The maximum amount of time that BGP will wait to receive End of RIB markers from all peers and for all address families that were up prior to restart.

           After this time elapses BGP declares that convergence has occurred and sends its own EOR markers to its peers.";
        type uint16 {
          range "0..3600";
        }
        units "seconds";
        default "600";
      }
    }
  }
}
